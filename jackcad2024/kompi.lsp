(load "c:/jackcad2024/subroutine/copyfolder")



(defun c:kompi ()
(vl-mkdir "D:\\jackcad2024")
(copyfolder "C:\\jackcad2024" "D:\\jackcad2024")

  
(if (/= (findfile "D:/jackcad2024/Topo/stoe._LS") nil)(vl-file-delete "D:/jackcad2024/Topo/stoe._LS"))
(if (/= (findfile "D:/jackcad2024/STANDAR/standar._LS") nil)(vl-file-delete "D:/jackcad2024/STANDAR/standar._LS"))
(if (/= (findfile "D:/jackcad2024/Runallstruct._LS") nil)(vl-file-delete "D:/jackcad2024/Runallstruct._LS"))
(if (/= (findfile "D:/jackcad2024/Terjunan/Terjuntersier._LS") nil)(vl-file-delete "D:/jackcad2024/Terjunan/Terjuntersier._LS"))
(if (/= (findfile "D:/jackcad2024/Terjunan/bacadataterjuntersier._LS") nil)(vl-file-delete "D:/jackcad2024/Terjunan/bacadataterjuntersier._LS"))
(if (/= (findfile "D:/jackcad2024/Terjunan/bacadataterjuntegak._LS") nil)(vl-file-delete "D:/jackcad2024/Terjunan/bacadataterjuntegak._LS"))
(if (/= (findfile "D:/jackcad2024/Terjunan/Terjuntegak._LS") nil)(vl-file-delete "D:/jackcad2024/Terjunan/Terjuntegak._LS"))
(if (/= (findfile "D:/jackcad2024/Terjunan/bacadataterjunmiring._LS") nil)(vl-file-delete "D:/jackcad2024/Terjunan/bacadataterjunmiring._LS"))
(if (/= (findfile "D:/jackcad2024/Terjunan/Terjunmiring._LS") nil)(vl-file-delete "D:/jackcad2024/Terjunan/Terjunmiring._LS"))
(if (/= (findfile "D:/jackcad2024/Boks/bacadatabox._LS") nil)(vl-file-delete "D:/jackcad2024/Boks/bacadatabox._LS"))
(if (/= (findfile "D:/jackcad2024/Boks/Boks._LS") nil)(vl-file-delete "D:/jackcad2024/Boks/Boks._LS"))
(if (/= (findfile "D:/jackcad2024/simbg._LS") nil)(vl-file-delete "D:/jackcad2024/simbg._LS"))
(if (/= (findfile "D:/jackcad2024/simde._LS") nil)(vl-file-delete "D:/jackcad2024/simde._LS"))
(if (/= (findfile "D:/jackcad2024/activ._LS") nil)(vl-file-delete "D:/jackcad2024/activ._LS"))
(if (/= (findfile "D:/jackcad2024/simtp._LS") nil)(vl-file-delete "D:/jackcad2024/simtp._LS"))
(if (/= (findfile "D:/jackcad2024/inputpw._LS") nil)(vl-file-delete "D:/jackcad2024/inputpw._LS"))
(if (/= (findfile "D:/jackcad2024/Topo/total._LS") nil)(vl-file-delete "D:/jackcad2024/Topo/total._LS"))
(if (/= (findfile "D:/jackcad2024/Topo/BM._LS") nil)(vl-file-delete "D:/jackcad2024/Topo/BM._LS"))
(if (/= (findfile "D:/jackcad2024/Topo/Runtopo._LS") nil)(vl-file-delete "D:/jackcad2024/Topo/Runtopo._LS"))
(if (/= (findfile "D:/jackcad2024/Topo/cross._LS") nil)(vl-file-delete "D:/jackcad2024/Topo/cross._LS"))
(if (/= (findfile "D:/jackcad2024/Topo/poligon._LS") nil)(vl-file-delete "D:/jackcad2024/Topo/poligon._LS"))
(if (/= (findfile "D:/jackcad2024/subroutine/bacadefault._LS") nil)(vl-file-delete "D:/jackcad2024/subroutine/bacadefault._LS"))
(if (/= (findfile "D:/jackcad2024/Long/pl1._LS") nil)(vl-file-delete "D:/jackcad2024/Long/pl1._LS"))
(if (/= (findfile "D:/jackcad2024/Long/hitungan._LS") nil)(vl-file-delete "D:/jackcad2024/Long/hitungan._LS"))
(if (/= (findfile "D:/jackcad2024/Long/tul-dim._LS") nil)(vl-file-delete "D:/jackcad2024/Long/tul-dim._LS"))
(if (/= (findfile "D:/jackcad2024/Long/RE-DIM._LS") nil)(vl-file-delete "D:/jackcad2024/Long/RE-DIM._LS"))
(if (/= (findfile "D:/jackcad2024/Long/DAT-EL._LS") nil)(vl-file-delete "D:/jackcad2024/Long/DAT-EL._LS"))
(if (/= (findfile "D:/jackcad2024/Long/irrpro._LS") nil)(vl-file-delete "D:/jackcad2024/Long/irrpro._LS"))
;;(if (/= (findfile "D:/jackcad2024/layout/layout._LS") nil)(vl-file-delete "D:/jackcad2024/layout/layout._LS"))
(if (/= (findfile "D:/jackcad2024/arah._LS") nil)(vl-file-delete "D:/jackcad2024/arah._LS"))
(if (/= (findfile "D:/jackcad2024/Lsp-lain/lain._LS") nil)(vl-file-delete "D:/jackcad2024/Lsp-lain/lain._LS"))
(if (/= (findfile "D:/jackcad2024/Proyek._LS") nil)(vl-file-delete "D:/jackcad2024/Proyek._LS"))
(if (/= (findfile "D:/jackcad2024/CROSS/CRpe._LS") nil)(vl-file-delete "D:/jackcad2024/CROSS/CRpe._LS"))
(if (/= (findfile "D:/jackcad2024/CROSS/C-main._LS") nil)(vl-file-delete "D:/jackcad2024/CROSS/C-main._LS"))
(if (/= (findfile "D:/jackcad2024/Topo/XYZ._LS") nil)(vl-file-delete "D:/jackcad2024/Topo/XYZ._LS"))
(if (/= (findfile "D:/jackcad2024/Topo/T-set._LS") nil)(vl-file-delete "D:/jackcad2024/Topo/T-set._LS"))
(if (/= (findfile "D:/jackcad2024/Topo/rubahdem._LS") nil)(vl-file-delete "D:/jackcad2024/Topo/rubahdem._LS"))
(if (/= (findfile "D:/jackcad2024/Topo/PLB._LS") nil)(vl-file-delete "D:/jackcad2024/Topo/PLB._LS"))
(if (/= (findfile "D:/jackcad2024/Topo/O-Sit._LS") nil)(vl-file-delete "D:/jackcad2024/Topo/O-Sit._LS"))
(if (/= (findfile "D:/jackcad2024/Topo/KOPILAY._LS") nil)(vl-file-delete "D:/jackcad2024/Topo/KOPILAY._LS"))
(if (/= (findfile "D:/jackcad2024/Topo/Kopi._LS") nil)(vl-file-delete "D:/jackcad2024/Topo/Kopi._LS"))
(if (/= (findfile "D:/jackcad2024/Topo/Kop-bang._LS") nil)(vl-file-delete "D:/jackcad2024/Topo/Kop-bang._LS"))
(if (/= (findfile "D:/jackcad2024/Topo/GRIDI._LS") nil)(vl-file-delete "D:/jackcad2024/Topo/GRIDI._LS"))
(if (/= (findfile "D:/jackcad2024/Topo/gbbang._LS") nil)(vl-file-delete "D:/jackcad2024/Topo/gbbang._LS"))
(if (/= (findfile "D:/jackcad2024/Topo/etb._LS") nil)(vl-file-delete "D:/jackcad2024/Topo/etb._LS"))
(if (/= (findfile "D:/jackcad2024/Topo/drb._LS") nil)(vl-file-delete "D:/jackcad2024/Topo/drb._LS"))
(if (/= (findfile "D:/jackcad2024/Topo/crosdem._LS") nil)(vl-file-delete "D:/jackcad2024/Topo/crosdem._LS"))
(if (/= (findfile "D:/jackcad2024/Topo/crd._LS") nil)(vl-file-delete "D:/jackcad2024/Topo/crd._LS"))
(if (/= (findfile "D:/jackcad2024/Topo/ANAK._LS") nil)(vl-file-delete "D:/jackcad2024/Topo/ANAK._LS"))
(if (/= (findfile "D:/jackcad2024/Terjunan/sub/terjunt2._LS") nil)(vl-file-delete "D:/jackcad2024/Terjunan/sub/terjunt2._LS"))
(if (/= (findfile "D:/jackcad2024/Terjunan/sub/terjunM2._LS") nil)(vl-file-delete "D:/jackcad2024/Terjunan/sub/terjunM2._LS"))
(if (/= (findfile "D:/jackcad2024/Terjunan/sub/terjun2._LS") nil)(vl-file-delete "D:/jackcad2024/Terjunan/sub/terjun2._LS"))
(if (/= (findfile "D:/jackcad2024/Terjunan/sub/longterjunt._LS") nil)(vl-file-delete "D:/jackcad2024/Terjunan/sub/longterjunt._LS"))
(if (/= (findfile "D:/jackcad2024/Terjunan/sub/longterjunm._LS") nil)(vl-file-delete "D:/jackcad2024/Terjunan/sub/longterjunm._LS"))
(if (/= (findfile "D:/jackcad2024/Terjunan/sub/longterjun._LS") nil)(vl-file-delete "D:/jackcad2024/Terjunan/sub/longterjun._LS"))
(if (/= (findfile "D:/jackcad2024/Terjunan/sub/longsal._LS") nil)(vl-file-delete "D:/jackcad2024/Terjunan/sub/longsal._LS"))
(if (/= (findfile "D:/jackcad2024/Terjunan/sub/denah-sal._LS") nil)(vl-file-delete "D:/jackcad2024/Terjunan/sub/denah-sal._LS"))
(if (/= (findfile "D:/jackcad2024/Terjunan/sub/crosterjunt._LS") nil)(vl-file-delete "D:/jackcad2024/Terjunan/sub/crosterjunt._LS"))
(if (/= (findfile "D:/jackcad2024/Terjunan/sub/crosterjunm._LS") nil)(vl-file-delete "D:/jackcad2024/Terjunan/sub/crosterjunm._LS"))
(if (/= (findfile "D:/jackcad2024/Terjunan/sub/crosterjun._LS") nil)(vl-file-delete "D:/jackcad2024/Terjunan/sub/crosterjun._LS"))
(if (/= (findfile "D:/jackcad2024/Terjunan/BACA-DATmiring._LS") nil)(vl-file-delete "D:/jackcad2024/Terjunan/BACA-DATmiring._LS"))
(if (/= (findfile "D:/jackcad2024/subroutine/bangunan/longsal._LS") nil)(vl-file-delete "D:/jackcad2024/subroutine/bangunan/longsal._LS"))
(if (/= (findfile "D:/jackcad2024/subroutine/bangunan/crosssaluran._LS") nil)(vl-file-delete "D:/jackcad2024/subroutine/bangunan/crosssaluran._LS"))
(if (/= (findfile "D:/jackcad2024/subroutine/bangunan/crossal2._LS") nil)(vl-file-delete "D:/jackcad2024/subroutine/bangunan/crossal2._LS"))
(if (/= (findfile "D:/jackcad2024/subroutine/skalasituasi._LS") nil)(vl-file-delete "D:/jackcad2024/subroutine/skalasituasi._LS"))
(if (/= (findfile "D:/jackcad2024/subroutine/lokasijudul._LS") nil)(vl-file-delete "D:/jackcad2024/subroutine/lokasijudul._LS"))
(if (/= (findfile "D:/jackcad2024/subroutine/formprogrambaru._LS") nil)(vl-file-delete "D:/jackcad2024/subroutine/formprogrambaru._LS"))
(if (/= (findfile "D:/jackcad2024/subroutine/cetakgambar._LS") nil)(vl-file-delete "D:/jackcad2024/subroutine/cetakgambar._LS"))
(if (/= (findfile "D:/jackcad2024/subroutine/ba_da._LS") nil)(vl-file-delete "D:/jackcad2024/subroutine/ba_da._LS"))
(if (/= (findfile "D:/jackcad2024/subroutine/bacanamaproyek._LS") nil)(vl-file-delete "D:/jackcad2024/subroutine/bacanamaproyek._LS"))
(if (/= (findfile "D:/jackcad2024/subroutine/awalprogram._LS") nil)(vl-file-delete "D:/jackcad2024/subroutine/awalprogram._LS"))
(if (/= (findfile "D:/jackcad2024/Sadap/sub/Denah/Pompa._LS") nil)(vl-file-delete "D:/jackcad2024/Sadap/sub/Denah/Pompa._LS"))
(if (/= (findfile "D:/jackcad2024/Sadap/sub/Denah/Gorong._LS") nil)(vl-file-delete "D:/jackcad2024/Sadap/sub/Denah/Gorong._LS"))
(if (/= (findfile "D:/jackcad2024/Sadap/sub/Denah/Dnsal._LS") nil)(vl-file-delete "D:/jackcad2024/Sadap/sub/Denah/Dnsal._LS"))
(if (/= (findfile "D:/jackcad2024/Sadap/sub/Denah/Ambang._LS") nil)(vl-file-delete "D:/jackcad2024/Sadap/sub/Denah/Ambang._LS"))
(if (/= (findfile "D:/jackcad2024/Sadap/sub/simbolair._LS") nil)(vl-file-delete "D:/jackcad2024/Sadap/sub/simbolair._LS"))
(if (/= (findfile "D:/jackcad2024/Sadap/sub/longsambungan._LS") nil)(vl-file-delete "D:/jackcad2024/Sadap/sub/longsambungan._LS"))
(if (/= (findfile "D:/jackcad2024/Sadap/sub/longsaluran._LS") nil)(vl-file-delete "D:/jackcad2024/Sadap/sub/longsaluran._LS"))
(if (/= (findfile "D:/jackcad2024/Sadap/sub/longpompa._LS") nil)(vl-file-delete "D:/jackcad2024/Sadap/sub/longpompa._LS"))
(if (/= (findfile "D:/jackcad2024/Sadap/sub/longbelok._LS") nil)(vl-file-delete "D:/jackcad2024/Sadap/sub/longbelok._LS"))
(if (/= (findfile "D:/jackcad2024/Sadap/sub/inmir._LS") nil)(vl-file-delete "D:/jackcad2024/Sadap/sub/inmir._LS"))
(if (/= (findfile "D:/jackcad2024/Sadap/sub/crospompa._LS") nil)(vl-file-delete "D:/jackcad2024/Sadap/sub/crospompa._LS"))
(if (/= (findfile "D:/jackcad2024/Sadap/Ukur._LS") nil)(vl-file-delete "D:/jackcad2024/Sadap/Ukur._LS"))
(if (/= (findfile "D:/jackcad2024/Sadap/Terjun._LS") nil)(vl-file-delete "D:/jackcad2024/Sadap/Terjun._LS"))
(if (/= (findfile "D:/jackcad2024/Sadap/Sadap._LS") nil)(vl-file-delete "D:/jackcad2024/Sadap/Sadap._LS"))
(if (/= (findfile "D:/jackcad2024/Sadap/BACA-DAT._LS") nil)(vl-file-delete "D:/jackcad2024/Sadap/BACA-DAT._LS"))
(if (/= (findfile "D:/jackcad2024/Lsp-lain/RM._LS") nil)(vl-file-delete "D:/jackcad2024/Lsp-lain/RM._LS"))
(if (/= (findfile "D:/jackcad2024/Long/Trase2._LS") nil)(vl-file-delete "D:/jackcad2024/Long/Trase2._LS"))
(if (/= (findfile "D:/jackcad2024/Long/Trase._LS") nil)(vl-file-delete "D:/jackcad2024/Long/Trase._LS"))
(if (/= (findfile "D:/jackcad2024/Long/O-long._LS") nil)(vl-file-delete "D:/jackcad2024/Long/O-long._LS"))
(if (/= (findfile "D:/jackcad2024/Long/Ld-set._LS") nil)(vl-file-delete "D:/jackcad2024/Long/Ld-set._LS"))
(if (/= (findfile "D:/jackcad2024/Long/ins-bgn._LS") nil)(vl-file-delete "D:/jackcad2024/Long/ins-bgn._LS"))
(if (/= (findfile "D:/jackcad2024/Long/grs-renc._LS") nil)(vl-file-delete "D:/jackcad2024/Long/grs-renc._LS"))
(if (/= (findfile "D:/jackcad2024/Long/GRS-RENC-step._LS") nil)(vl-file-delete "D:/jackcad2024/Long/GRS-RENC-step._LS"))
(if (/= (findfile "D:/jackcad2024/CROSS/tnh-as._LS") nil)(vl-file-delete "D:/jackcad2024/CROSS/tnh-as._LS"))
;;(if (/= (findfile "D:/jackcad2024/CROSS/Skatul._LS") nil)(vl-file-delete "D:/jackcad2024/CROSS/Skatul._LS"))
(if (/= (findfile "D:/jackcad2024/CROSS/sal-renc._LS") nil)(vl-file-delete "D:/jackcad2024/CROSS/sal-renc._LS"))
(if (/= (findfile "D:/jackcad2024/CROSS/SAL-RENC-tn._LS") nil)(vl-file-delete "D:/jackcad2024/CROSS/SAL-RENC-tn._LS"))
(if (/= (findfile "D:/jackcad2024/CROSS/SAL-RENC-step._LS") nil)(vl-file-delete "D:/jackcad2024/CROSS/SAL-RENC-step._LS"))
(if (/= (findfile "D:/jackcad2024/CROSS/O-cros._LS") nil)(vl-file-delete "D:/jackcad2024/CROSS/O-cros._LS"))
(if (/= (findfile "D:/jackcad2024/CROSS/NC._LS") nil)(vl-file-delete "D:/jackcad2024/CROSS/NC._LS"))
(if (/= (findfile "D:/jackcad2024/CROSS/bat-bebas._LS") nil)(vl-file-delete "D:/jackcad2024/CROSS/bat-bebas._LS"))
(if (/= (findfile "D:/jackcad2024/Boks/sub/Sal6c._LS") nil)(vl-file-delete "D:/jackcad2024/Boks/sub/Sal6c._LS"))
(if (/= (findfile "D:/jackcad2024/Boks/sub/Sal6b._LS") nil)(vl-file-delete "D:/jackcad2024/Boks/sub/Sal6b._LS"))
(if (/= (findfile "D:/jackcad2024/Boks/sub/Sal6._LS") nil)(vl-file-delete "D:/jackcad2024/Boks/sub/Sal6._LS"))
(if (/= (findfile "D:/jackcad2024/Boks/sub/Sal4i._LS") nil)(vl-file-delete "D:/jackcad2024/Boks/sub/Sal4i._LS"))
(if (/= (findfile "D:/jackcad2024/Boks/sub/Sal4h._LS") nil)(vl-file-delete "D:/jackcad2024/Boks/sub/Sal4h._LS"))
(if (/= (findfile "D:/jackcad2024/Boks/sub/Sal4g._LS") nil)(vl-file-delete "D:/jackcad2024/Boks/sub/Sal4g._LS"))
(if (/= (findfile "D:/jackcad2024/Boks/sub/Sal4f._LS") nil)(vl-file-delete "D:/jackcad2024/Boks/sub/Sal4f._LS"))
(if (/= (findfile "D:/jackcad2024/Boks/sub/Sal4e._LS") nil)(vl-file-delete "D:/jackcad2024/Boks/sub/Sal4e._LS"))
(if (/= (findfile "D:/jackcad2024/Boks/sub/Sal4d._LS") nil)(vl-file-delete "D:/jackcad2024/Boks/sub/Sal4d._LS"))
(if (/= (findfile "D:/jackcad2024/Boks/sub/Sal4c._LS") nil)(vl-file-delete "D:/jackcad2024/Boks/sub/Sal4c._LS"))
(if (/= (findfile "D:/jackcad2024/Boks/sub/Sal4b._LS") nil)(vl-file-delete "D:/jackcad2024/Boks/sub/Sal4b._LS"))
(if (/= (findfile "D:/jackcad2024/Boks/sub/Sal4._LS") nil)(vl-file-delete "D:/jackcad2024/Boks/sub/Sal4._LS"))
(if (/= (findfile "D:/jackcad2024/Boks/sub/Sal2c._LS") nil)(vl-file-delete "D:/jackcad2024/Boks/sub/Sal2c._LS"))
(if (/= (findfile "D:/jackcad2024/Boks/sub/Sal2b._LS") nil)(vl-file-delete "D:/jackcad2024/Boks/sub/Sal2b._LS"))
(if (/= (findfile "D:/jackcad2024/Boks/sub/Sal2._LS") nil)(vl-file-delete "D:/jackcad2024/Boks/sub/Sal2._LS"))
(if (/= (findfile "D:/jackcad2024/Boks/sub/Sal1._LS") nil)(vl-file-delete "D:/jackcad2024/Boks/sub/Sal1._LS"))
(if (/= (findfile "D:/jackcad2024/Boks/sub/PML6bc._LS") nil)(vl-file-delete "D:/jackcad2024/Boks/sub/PML6bc._LS"))
(if (/= (findfile "D:/jackcad2024/Boks/sub/PML6._LS") nil)(vl-file-delete "D:/jackcad2024/Boks/sub/PML6._LS"))
(if (/= (findfile "D:/jackcad2024/Boks/sub/PML4fghi._LS") nil)(vl-file-delete "D:/jackcad2024/Boks/sub/PML4fghi._LS"))
(if (/= (findfile "D:/jackcad2024/Boks/sub/PML4de._LS") nil)(vl-file-delete "D:/jackcad2024/Boks/sub/PML4de._LS"))
(if (/= (findfile "D:/jackcad2024/Boks/sub/PML4BC._LS") nil)(vl-file-delete "D:/jackcad2024/Boks/sub/PML4BC._LS"))
(if (/= (findfile "D:/jackcad2024/Boks/sub/PML4._LS") nil)(vl-file-delete "D:/jackcad2024/Boks/sub/PML4._LS"))
(if (/= (findfile "D:/jackcad2024/Boks/sub/PML2bc._LS") nil)(vl-file-delete "D:/jackcad2024/Boks/sub/PML2bc._LS"))
(if (/= (findfile "D:/jackcad2024/Boks/sub/PML2._LS") nil)(vl-file-delete "D:/jackcad2024/Boks/sub/PML2._LS"))
(if (/= (findfile "D:/jackcad2024/Boks/sub/PMl1._LS") nil)(vl-file-delete "D:/jackcad2024/Boks/sub/PMl1._LS"))
(if (/= (findfile "D:/jackcad2024/Boks/sub/pl3._LS") nil)(vl-file-delete "D:/jackcad2024/Boks/sub/pl3._LS"))
(if (/= (findfile "D:/jackcad2024/Boks/sub/pl2._LS") nil)(vl-file-delete "D:/jackcad2024/Boks/sub/pl2._LS"))
(if (/= (findfile "D:/jackcad2024/Boks/sub/pl1._LS") nil)(vl-file-delete "D:/jackcad2024/Boks/sub/pl1._LS"))
(if (/= (findfile "D:/jackcad2024/Boks/sub/Longc2._LS") nil)(vl-file-delete "D:/jackcad2024/Boks/sub/Longc2._LS"))
(if (/= (findfile "D:/jackcad2024/Boks/sub/Longc1._LS") nil)(vl-file-delete "D:/jackcad2024/Boks/sub/Longc1._LS"))
(if (/= (findfile "D:/jackcad2024/Boks/sub/Longb5._LS") nil)(vl-file-delete "D:/jackcad2024/Boks/sub/Longb5._LS"))
(if (/= (findfile "D:/jackcad2024/Boks/sub/Longb4._LS") nil)(vl-file-delete "D:/jackcad2024/Boks/sub/Longb4._LS"))
(if (/= (findfile "D:/jackcad2024/Boks/sub/Longb3._LS") nil)(vl-file-delete "D:/jackcad2024/Boks/sub/Longb3._LS"))
(if (/= (findfile "D:/jackcad2024/Boks/sub/Longb2._LS") nil)(vl-file-delete "D:/jackcad2024/Boks/sub/Longb2._LS"))
(if (/= (findfile "D:/jackcad2024/Boks/sub/Longb1._LS") nil)(vl-file-delete "D:/jackcad2024/Boks/sub/Longb1._LS"))
(if (/= (findfile "D:/jackcad2024/Boks/sub/Longa3._LS") nil)(vl-file-delete "D:/jackcad2024/Boks/sub/Longa3._LS"))
(if (/= (findfile "D:/jackcad2024/Boks/sub/Longa2._LS") nil)(vl-file-delete "D:/jackcad2024/Boks/sub/Longa2._LS"))
(if (/= (findfile "D:/jackcad2024/Boks/sub/Long1._LS") nil)(vl-file-delete "D:/jackcad2024/Boks/sub/Long1._LS"))
(if (/= (findfile "D:/jackcad2024/bangunan/o-bangunan._LS") nil)(vl-file-delete "D:/jackcad2024/bangunan/o-bangunan._LS"))
(if (/= (findfile "D:/jackcad2024/TU-SET._LS") nil)(vl-file-delete "D:/jackcad2024/TU-SET._LS"))
(if (/= (findfile "D:/jackcad2024/RE-SET._LS") nil)(vl-file-delete "D:/jackcad2024/RE-SET._LS"))
(if (/= (findfile "D:/jackcad2024/Pter._LS") nil)(vl-file-delete "D:/jackcad2024/Pter._LS"))
(if (/= (findfile "D:/jackcad2024/Pkwar._LS") nil)(vl-file-delete "D:/jackcad2024/Pkwar._LS"))
(if (/= (findfile "D:/jackcad2024/op-file._LS") nil)(vl-file-delete "D:/jackcad2024/op-file._LS"))
(if (/= (findfile "D:/jackcad2024/Boks/sub/KOTAK._LS") nil)(vl-file-delete "D:/jackcad2024/Boks/sub/KOTAK._LS"))
(if (/= (findfile "D:/jackcad2024/subroutine/arsirmiring._LS") nil)(vl-file-delete "D:/jackcad2024/subroutine/arsirmiring._LS"))
(if (/= (findfile "D:/jackcad2024/subroutine/arsirtanah._LS") nil)(vl-file-delete "D:/jackcad2024/subroutine/arsirtanah._LS"))
(if (/= (findfile "D:/jackcad2024/subroutine/hatchmiring._LS") nil)(vl-file-delete "D:/jackcad2024/subroutine/hatchmiring._LS"))
(if (/= (findfile "D:/jackcad2024/CROSS/re-dim._LS") nil)(vl-file-delete "D:/jackcad2024/CROSS/re-dim._LS"))
(if (/= (findfile "D:/jackcad2024/CROSS/pasangan._LS") nil)(vl-file-delete "D:/jackcad2024/CROSS/pasangan._LS"))
(if (/= (findfile "D:/jackcad2024/CROSS/car-lok._LS") nil)(vl-file-delete "D:/jackcad2024/CROSS/car-lok._LS"))
(if (/= (findfile "D:/jackcad2024/Sadap/sub/crossal._LS") nil)(vl-file-delete "D:/jackcad2024/Sadap/sub/crossal._LS"))
(if (/= (findfile "D:/jackcad2024/Sadap/sub/KO-TEK2._LS") nil)(vl-file-delete "D:/jackcad2024/Sadap/sub/KO-TEK2._LS"))
(if (/= (findfile "D:/jackcad2024/Sadap/sub/BOQ/Boqsaluran._LS") nil)(vl-file-delete "D:/jackcad2024/Sadap/sub/BOQ/Boqsaluran._LS"))
(if (/= (findfile "D:/jackcad2024/Sadap/sub/dimsal._LS") nil)(vl-file-delete "D:/jackcad2024/Sadap/sub/dimsal._LS"))
(if (/= (findfile "D:/jackcad2024/subroutine/serialnumber._LS") nil)(vl-file-delete "D:/jackcad2024/subroutine/serialnumber._LS"))
(if (/= (findfile "D:/jackcad2024/subroutine/snc._LS") nil)(vl-file-delete "D:/jackcad2024/subroutine/snc._LS"))
(if (/= (findfile "D:/jackcad2024/subroutine/copyfolder._LS") nil)(vl-file-delete "D:/jackcad2024/subroutine/copyfolder._LS"))
(if (/= (findfile "D:/jackcad2024/Sadap/RM2._LS") nil)(vl-file-delete "D:/jackcad2024/Sadap/RM2._LS"))
(if (/= (findfile "D:/jackcad2024/Sadap/sub/crospintu._LS") nil)(vl-file-delete "D:/jackcad2024/Sadap/sub/crospintu._LS"))
(if (/= (findfile "D:/jackcad2024/Sadap/sub/longpintu._LS") nil)(vl-file-delete "D:/jackcad2024/Sadap/sub/longpintu._LS"))
(if (/= (findfile "D:/jackcad2024/Sadap/sub/longgorong._LS") nil)(vl-file-delete "D:/jackcad2024/Sadap/sub/longgorong._LS"))
(if (/= (findfile "D:/jackcad2024/Sadap/sub/crosgorong._LS") nil)(vl-file-delete "D:/jackcad2024/Sadap/sub/crosgorong._LS"))
(if (/= (findfile "D:/jackcad2024/Sadap/sub/longambang._LS") nil)(vl-file-delete "D:/jackcad2024/Sadap/sub/longambang._LS"))
(if (/= (findfile "D:/jackcad2024/Sadap/sub/awalkotak._LS") nil)(vl-file-delete "D:/jackcad2024/Sadap/sub/awalkotak._LS"))
(if (/= (findfile "D:/jackcad2024/Sadap/sub/crosambang._LS") nil)(vl-file-delete "D:/jackcad2024/Sadap/sub/crosambang._LS"))
(if (/= (findfile "D:/jackcad2024/subroutine/TeksDimensi._LS") nil)(vl-file-delete "D:/jackcad2024/subroutine/TeksDimensi._LS"))
(if (/= (findfile "D:/jackcad2024/subroutine/settinghuruf._LS") nil)(vl-file-delete "D:/jackcad2024/subroutine/settinghuruf._LS"))
(if (/= (findfile "D:/jackcad2024/subroutine/teks-elevasi._LS") nil)(vl-file-delete "D:/jackcad2024/subroutine/teks-elevasi._LS"))
(if (/= (findfile "D:/jackcad2024/Sadap/sub/T-E._LS") nil)(vl-file-delete "D:/jackcad2024/Sadap/sub/T-E._LS"))
(if (/= (findfile "D:/jackcad2024/Sadap/sub/sdbulat._LS") nil)(vl-file-delete "D:/jackcad2024/Sadap/sub/sdbulat._LS"))
(if (/= (findfile "D:/jackcad2024/Sadap/sub/belno._LS") nil)(vl-file-delete "D:/jackcad2024/Sadap/sub/belno._LS"))
(if (/= (findfile "D:/jackcad2024/Sadap/sub/MR1a._LS") nil)(vl-file-delete "D:/jackcad2024/Sadap/sub/MR1a._LS"))
(if (/= (findfile "D:/jackcad2024/Sadap/sub/awalsdakhir._LS") nil)(vl-file-delete "D:/jackcad2024/Sadap/sub/awalsdakhir._LS"))
(if (/= (findfile "D:/jackcad2024/Sadap/sub/settingsaluranawal._LS") nil)(vl-file-delete "D:/jackcad2024/Sadap/sub/settingsaluranawal._LS"))
(if (/= (findfile "D:/jackcad2024/Sadap/sub/settingsaluranakhir._LS") nil)(vl-file-delete "D:/jackcad2024/Sadap/sub/settingsaluranakhir._LS"))
(if (/= (findfile "D:/jackcad2024/Sadap/sub/dimlama._LS") nil)(vl-file-delete "D:/jackcad2024/Sadap/sub/dimlama._LS"))
(if (/= (findfile "D:/jackcad2024/Long/tul-leng._LS") nil)(vl-file-delete "D:/jackcad2024/Long/tul-leng._LS"))
(if (/= (findfile "D:/jackcad2024/Long/da-long._LS") nil)(vl-file-delete "D:/jackcad2024/Long/da-long._LS"))
(if (/= (findfile "D:/jackcad2024/Long/FKURVA._LS") nil)(vl-file-delete "D:/jackcad2024/Long/FKURVA._LS"))
(if (/= (findfile "D:/jackcad2024/CROSS/te-ja._LS") nil)(vl-file-delete "D:/jackcad2024/CROSS/te-ja._LS"))
(if (/= (findfile "D:/jackcad2024/CROSS/aturc._LS") nil)(vl-file-delete "D:/jackcad2024/CROSS/aturc._LS"))
(if (/= (findfile "D:/jackcad2024/CROSS/tul-dim._LS") nil)(vl-file-delete "D:/jackcad2024/CROSS/tul-dim._LS"))
(if (/= (findfile "D:/jackcad2024/CROSS/TUL-DIM-step._LS") nil)(vl-file-delete "D:/jackcad2024/CROSS/TUL-DIM-step._LS"))
(if (/= (findfile "D:/jackcad2024/CROSS/tul-datpat._LS") nil)(vl-file-delete "D:/jackcad2024/CROSS/tul-datpat._LS"))
(if (/= (findfile "D:/jackcad2024/CROSS/T-E._LS") nil)(vl-file-delete "D:/jackcad2024/CROSS/T-E._LS"))
(if (/= (findfile "D:/jackcad2024/CROSS/jalan._LS") nil)(vl-file-delete "D:/jackcad2024/CROSS/jalan._LS"))
(if (/= (findfile "D:/jackcad2024/CROSS/gam._LS") nil)(vl-file-delete "D:/jackcad2024/CROSS/gam._LS"))
(if (/= (findfile "D:/jackcad2024/Long/TUL-DAT._LS") nil)(vl-file-delete "D:/jackcad2024/Long/TUL-DAT._LS"))
(if (/= (findfile "D:/jackcad2024/Long/TUL-DAT-step._LS") nil)(vl-file-delete "D:/jackcad2024/Long/TUL-DAT-step._LS"))
(if (/= (findfile "D:/jackcad2024/Long/SKALA-V._LS") nil)(vl-file-delete "D:/jackcad2024/Long/SKALA-V._LS"))
(if (/= (findfile "D:/jackcad2024/Long/hektom._LS") nil)(vl-file-delete "D:/jackcad2024/Long/hektom._LS"))
(if (/= (findfile "D:/jackcad2024/Long/TUL-DIM-step._LS") nil)(vl-file-delete "D:/jackcad2024/Long/TUL-DIM-step._LS"))
(if (/= (findfile "D:/jackcad2024/Long/D-C2._LS") nil)(vl-file-delete "D:/jackcad2024/Long/D-C2._LS"))
(if (/= (findfile "D:/jackcad2024/Long/D-C1._LS") nil)(vl-file-delete "D:/jackcad2024/Long/D-C1._LS"))
(if (/= (findfile "D:/jackcad2024/Long/DIMDRAIN._LS") nil)(vl-file-delete "D:/jackcad2024/Long/DIMDRAIN._LS"))
(if (/= (findfile "D:/jackcad2024/Long/DIMCANAL._LS") nil)(vl-file-delete "D:/jackcad2024/Long/DIMCANAL._LS"))
(if (/= (findfile "D:/jackcad2024/bangunan/aturBangunan._LS") nil)(vl-file-delete "D:/jackcad2024/bangunan/aturBangunan._LS"))
(if (/= (findfile "D:/jackcad2024/Topo/Bacadatasituasi._LS") nil)(vl-file-delete "D:/jackcad2024/Topo/Bacadatasituasi._LS"))
(if (/= (findfile "D:/jackcad2024/Topo/aturS._LS") nil)(vl-file-delete "D:/jackcad2024/Topo/aturS._LS"))
(if (/= (findfile "D:/jackcad2024/subroutine/setqp._LS") nil)(vl-file-delete "D:/jackcad2024/subroutine/setqp._LS"))
(if (/= (findfile "D:/jackcad2024/subroutine/daftarautolip._LS") nil)(vl-file-delete "D:/jackcad2024/subroutine/daftarautolip._LS"))
(if (/= (findfile "D:/jackcad2024/CROSS/warna._LS") nil)(vl-file-delete "D:/jackcad2024/CROSS/warna._LS"))
(if (/= (findfile "D:/jackcad2024/subroutine/bangunan/tip-PAS._LS") nil)(vl-file-delete "D:/jackcad2024/subroutine/bangunan/tip-PAS._LS"))
(if (/= (findfile "D:/jackcad2024/arsir4._LS") nil)(vl-file-delete "D:/jackcad2024/arsir4._LS"))
(if (/= (findfile "D:/jackcad2024/Terjunan/sub/KO-TEK._LS") nil)(vl-file-delete "D:/jackcad2024/Terjunan/sub/KO-TEK._LS"))
(if (/= (findfile "D:/jackcad2024/inisial._LS") nil)(vl-file-delete "D:/jackcad2024/inisial._LS"))
(if (/= (findfile "D:/jackcad2024/subroutine/inisial._LS") nil)(vl-file-delete "D:/jackcad2024/subroutine/inisial._LS"))
;;;(if (/= (findfile "D:/jackcad2024/subroutine/rubahukuranhuruf._LS") nil)(vl-file-delete "D:/jackcad2024/subroutine/rubahukuranhuruf._LS"))
(if (/= (findfile "D:/jackcad2024/subroutine/rubahelevasi._LS") nil)(vl-file-delete "D:/jackcad2024/subroutine/rubahelevasi._LS"))
(if (/= (findfile "D:/jackcad2024/subroutine/putartext._LS") nil)(vl-file-delete "D:/jackcad2024/subroutine/putartext._LS"))
(if (/= (findfile "D:/jackcad2024/subroutine/bacadataformtab._LS") nil)(vl-file-delete "D:/jackcad2024/subroutine/bacadataformtab._LS"))
(if (/= (findfile "D:/jackcad2024/subroutine/bacadataexcel._LS") nil)(vl-file-delete "D:/jackcad2024/subroutine/bacadataexcel._LS"))
(if (/= (findfile "D:/jackcad2024/subroutine/azimuth._LS") nil)(vl-file-delete "D:/jackcad2024/subroutine/azimuth._LS"))
(if (/= (findfile "D:/jackcad2024/subroutine/bacalokjudul._LS") nil)(vl-file-delete "D:/jackcad2024/subroutine/bacalokjudul._LS"))
(if (/= (findfile "D:/jackcad2024/subroutine/bangunan/Kotakdimensi._LS") nil)(vl-file-delete "D:/jackcad2024/subroutine/bangunan/Kotakdimensi._LS"))
(if (/= (findfile "D:/jackcad2024/Boks/sub/KO-TEK._LS") nil)(vl-file-delete "D:/jackcad2024/Boks/sub/KO-TEK._LS"))
(if (/= (findfile "D:/jackcad2024/subroutine/Browsefolder._LS") nil)(vl-file-delete "D:/jackcad2024/subroutine/Browsefolder._LS"))
(if (/= (findfile "D:/jackcad2024/CROSS/re-fi._LS") nil)(vl-file-delete "D:/jackcad2024/CROSS/re-fi._LS"))
(if (/= (findfile "D:/jackcad2024/Long/tip-PAS._LS") nil)(vl-file-delete "D:/jackcad2024/Long/tip-PAS._LS"))
;;(if (/= (findfile "D:/jackcad2024/CROSS/Skat_l._LS") nil)(vl-file-delete "D:/jackcad2024/CROSS/Skat_l._LS"))
(if (/= (findfile "D:/jackcad2024/Sadap/sub/BOQ/boqpompa._LS") nil)(vl-file-delete "D:/jackcad2024/Sadap/sub/BOQ/boqpompa._LS"))
(if (/= (findfile "D:/jackcad2024/Sadap/sub/BOQ/boqambang._LS") nil)(vl-file-delete "D:/jackcad2024/Sadap/sub/BOQ/boqambang._LS"))
(if (/= (findfile "D:/jackcad2024/Sadap/sub/BOQ/boqgorong._LS") nil)(vl-file-delete "D:/jackcad2024/Sadap/sub/BOQ/boqgorong._LS"))
(if (/= (findfile "D:/jackcad2024/Sadap/sub/BOQ/boqsambungan._LS") nil)(vl-file-delete "D:/jackcad2024/Sadap/sub/BOQ/boqsambungan._LS"))
(if (/= (findfile "D:/jackcad2024/Sadap/sub/BOQ/boqpintu._LS") nil)(vl-file-delete "D:/jackcad2024/Sadap/sub/BOQ/boqpintu._LS"))
(if (/= (findfile "D:/jackcad2024/Sadap/sub/BOQ/boqbelokan._LS") nil)(vl-file-delete "D:/jackcad2024/Sadap/sub/BOQ/boqbelokan._LS"))
(if (/= (findfile "D:/jackcad2024/Sadap/sub/setlay._LS") nil)(vl-file-delete "D:/jackcad2024/Sadap/sub/setlay._LS"))
(if (/= (findfile "D:/jackcad2024/Sadap/sub/Denah/Pintu._LS") nil)(vl-file-delete "D:/jackcad2024/Sadap/sub/Denah/Pintu._LS"))
(if (/= (findfile "D:/jackcad2024/Sadap/sub/koperup._LS") nil)(vl-file-delete "D:/jackcad2024/Sadap/sub/koperup._LS"))
(if (/= (findfile "D:/jackcad2024/Sadap/carilokasi._LS") nil)(vl-file-delete "D:/jackcad2024/Sadap/carilokasi._LS"))
(if (/= (findfile "D:/jackcad2024/Sadap/sub/Denah/Dnbelok._LS") nil)(vl-file-delete "D:/jackcad2024/Sadap/sub/Denah/Dnbelok._LS"))
(if (/= (findfile "D:/jackcad2024/Sadap/sub/Denah/sambungan._LS") nil)(vl-file-delete "D:/jackcad2024/Sadap/sub/Denah/sambungan._LS"))
(if (/= (findfile "D:/jackcad2024/Sadap/sub/Dnpier._LS") nil)(vl-file-delete "D:/jackcad2024/Sadap/sub/Dnpier._LS"))
(if (/= (findfile "D:/jackcad2024/Sadap/sub/Dnpusat._LS") nil)(vl-file-delete "D:/jackcad2024/Sadap/sub/Dnpusat._LS"))
(if (/= (findfile "D:/jackcad2024/Sadap/sub/DtRd._LS") nil)(vl-file-delete "D:/jackcad2024/Sadap/sub/DtRd._LS"))
(if (/= (findfile "D:/jackcad2024/Sadap/sub/RM4._LS") nil)(vl-file-delete "D:/jackcad2024/Sadap/sub/RM4._LS"))
(if (/= (findfile "D:/jackcad2024/Sadap/sub/MR1._LS") nil)(vl-file-delete "D:/jackcad2024/Sadap/sub/MR1._LS"))
(if (/= (findfile "D:/jackcad2024/Sadap/sub/Dnpin._LS") nil)(vl-file-delete "D:/jackcad2024/Sadap/sub/Dnpin._LS"))
(if (/= (findfile "D:/jackcad2024/Sadap/sub/MR4._LS") nil)(vl-file-delete "D:/jackcad2024/Sadap/sub/MR4._LS"))
(if (/= (findfile "D:/jackcad2024/Sadap/sub/Melintang/jenislining._LS") nil)(vl-file-delete "D:/jackcad2024/Sadap/sub/Melintang/jenislining._LS"))
(if (/= (findfile "D:/jackcad2024/Sadap/nl._LS") nil)(vl-file-delete "D:/jackcad2024/Sadap/nl._LS"))
(if (/= (findfile "D:/jackcad2024/nilai._LS") nil)(vl-file-delete "D:/jackcad2024/nilai._LS"))
(if (/= (findfile "D:/jackcad2024/tam+._LS") nil)(vl-file-delete "D:/jackcad2024/tam+._LS"))
(if (/= (findfile "D:/jackcad2024/Lsp-lain/lng._LS") nil)(vl-file-delete "D:/jackcad2024/Lsp-lain/lng._LS"))
(if (/= (findfile "D:/jackcad2024/contoh/Setting/ATURL._LS") nil)(vl-file-delete "D:/jackcad2024/contoh/Setting/ATURL._LS"))
(if (/= (findfile "D:/jackcad2024/Formkosong/Setting/ATURL._LS") nil)(vl-file-delete "D:/jackcad2024/Formkosong/Setting/ATURL._LS"))
(if (/= (findfile "D:/jackcad2024/contoh/Setting/ATURC._LS") nil)(vl-file-delete "D:/jackcad2024/contoh/Setting/ATURC._LS"))
(if (/= (findfile "D:/jackcad2024/Formkosong/Setting/ATURC._LS") nil)(vl-file-delete "D:/jackcad2024/Formkosong/Setting/ATURC._LS"))
(if (/= (findfile "D:/jackcad2024/rubahdat._LS") nil)(vl-file-delete "D:/jackcad2024/rubahdat._LS"))
(if (/= (findfile "D:/jackcad2024/Terjunan/sub/RM1._LS") nil)(vl-file-delete "D:/jackcad2024/Terjunan/sub/RM1._LS"))
(if (/= (findfile "D:/jackcad2024/Boks/sub/KOPER._LS") nil)(vl-file-delete "D:/jackcad2024/Boks/sub/KOPER._LS"))
(if (/= (findfile "D:/jackcad2024/Boks/sub/RM._LS") nil)(vl-file-delete "D:/jackcad2024/Boks/sub/RM._LS"))
(if (/= (findfile "D:/jackcad2024/Boks/sub/RM2._LS") nil)(vl-file-delete "D:/jackcad2024/Boks/sub/RM2._LS"))
(if (/= (findfile "D:/jackcad2024/CROSS/C-drain._LS") nil)(vl-file-delete "D:/jackcad2024/CROSS/C-drain._LS"))
(if (/= (findfile "D:/jackcad2024/CROSS/C-ter._LS") nil)(vl-file-delete "D:/jackcad2024/CROSS/C-ter._LS"))
(if (/= (findfile "D:/jackcad2024/CROSS/CAR-LOK-step._LS") nil)(vl-file-delete "D:/jackcad2024/CROSS/CAR-LOK-step._LS"))
(if (/= (findfile "D:/jackcad2024/CROSS/centerline._LS") nil)(vl-file-delete "D:/jackcad2024/CROSS/centerline._LS"))
(if (/= (findfile "D:/jackcad2024/CROSS/GALTIM._LS") nil)(vl-file-delete "D:/jackcad2024/CROSS/GALTIM._LS"))
(if (/= (findfile "D:/jackcad2024/CROSS/GRS-TN._LS") nil)(vl-file-delete "D:/jackcad2024/CROSS/GRS-TN._LS"))
(if (/= (findfile "D:/jackcad2024/CROSS/Ins-das._LS") nil)(vl-file-delete "D:/jackcad2024/CROSS/Ins-das._LS"))
(if (/= (findfile "D:/jackcad2024/CROSS/KUPAS._LS") nil)(vl-file-delete "D:/jackcad2024/CROSS/KUPAS._LS"))
(if (/= (findfile "D:/jackcad2024/CROSS/KUPASAN._LS") nil)(vl-file-delete "D:/jackcad2024/CROSS/KUPASAN._LS"))
(if (/= (findfile "D:/jackcad2024/CROSS/LUASAN._LS") nil)(vl-file-delete "D:/jackcad2024/CROSS/LUASAN._LS"))
(if (/= (findfile "D:/jackcad2024/CROSS/POTONG._LS") nil)(vl-file-delete "D:/jackcad2024/CROSS/POTONG._LS"))
(if (/= (findfile "D:/jackcad2024/CROSS/POTONG2._LS") nil)(vl-file-delete "D:/jackcad2024/CROSS/POTONG2._LS"))
(if (/= (findfile "D:/jackcad2024/CROSS/RE-DIM-step._LS") nil)(vl-file-delete "D:/jackcad2024/CROSS/RE-DIM-step._LS"))
(if (/= (findfile "D:/jackcad2024/CROSS/RU-DAT._LS") nil)(vl-file-delete "D:/jackcad2024/CROSS/RU-DAT._LS"))
(if (/= (findfile "D:/jackcad2024/CROSS/SET-JRK._LS") nil)(vl-file-delete "D:/jackcad2024/CROSS/SET-JRK._LS"))
(if (/= (findfile "D:/jackcad2024/CROSS/Set-ltk._LS") nil)(vl-file-delete "D:/jackcad2024/CROSS/Set-ltk._LS"))
(if (/= (findfile "D:/jackcad2024/Long/1LEMBAR._LS") nil)(vl-file-delete "D:/jackcad2024/Long/1LEMBAR._LS"))
(if (/= (findfile "D:/jackcad2024/Long/ATURL._LS") nil)(vl-file-delete "D:/jackcad2024/Long/ATURL._LS"))
(if (/= (findfile "D:/jackcad2024/Long/DA-LENG._LS") nil)(vl-file-delete "D:/jackcad2024/Long/DA-LENG._LS"))
(if (/= (findfile "D:/jackcad2024/Long/DA-LONG-step._LS") nil)(vl-file-delete "D:/jackcad2024/Long/DA-LONG-step._LS"))
(if (/= (findfile "D:/jackcad2024/Long/DAMAXMIN._LS") nil)(vl-file-delete "D:/jackcad2024/Long/DAMAXMIN._LS"))
(if (/= (findfile "D:/jackcad2024/Long/DAT-EL-step._LS") nil)(vl-file-delete "D:/jackcad2024/Long/DAT-EL-step._LS"))
(if (/= (findfile "D:/jackcad2024/Long/DELTEXT._LS") nil)(vl-file-delete "D:/jackcad2024/Long/DELTEXT._LS"))
(if (/= (findfile "D:/jackcad2024/Long/FGARIS._LS") nil)(vl-file-delete "D:/jackcad2024/Long/FGARIS._LS"))
(if (/= (findfile "D:/jackcad2024/Long/FGARIS2._LS") nil)(vl-file-delete "D:/jackcad2024/Long/FGARIS2._LS"))
(if (/= (findfile "D:/jackcad2024/Long/FKURVA2._LS") nil)(vl-file-delete "D:/jackcad2024/Long/FKURVA2._LS"))
(if (/= (findfile "D:/jackcad2024/Long/Ins-kop._LS") nil)(vl-file-delete "D:/jackcad2024/Long/Ins-kop._LS"))
(if (/= (findfile "D:/jackcad2024/Long/L-drain._LS") nil)(vl-file-delete "D:/jackcad2024/Long/L-drain._LS"))
(if (/= (findfile "D:/jackcad2024/Long/L-main._LS") nil)(vl-file-delete "D:/jackcad2024/Long/L-main._LS"))
(if (/= (findfile "D:/jackcad2024/Long/L-ter._LS") nil)(vl-file-delete "D:/jackcad2024/Long/L-ter._LS"))
(if (/= (findfile "D:/jackcad2024/Long/RE-DIM-step._LS") nil)(vl-file-delete "D:/jackcad2024/Long/RE-DIM-step._LS"))
(if (/= (findfile "D:/jackcad2024/Long/RE-DIM-stepL._LS") nil)(vl-file-delete "D:/jackcad2024/Long/RE-DIM-stepL._LS"))
(if (/= (findfile "D:/jackcad2024/Long/RE-SDT._LS") nil)(vl-file-delete "D:/jackcad2024/Long/RE-SDT._LS"))
(if (/= (findfile "D:/jackcad2024/Lsp-lain/RM2._LS") nil)(vl-file-delete "D:/jackcad2024/Lsp-lain/RM2._LS"))
(if (/= (findfile "D:/jackcad2024/Sadap/RM._LS") nil)(vl-file-delete "D:/jackcad2024/Sadap/RM._LS"))


(if (/= (findfile "D:/jackcad2024/Topo/stoe.LSP") nil)(vlisp-compile 'st "D:/jackcad2024/Topo/stoe.LSP"))
(if (/= (findfile "D:/jackcad2024/STANDAR/standar.LSP") nil)(vlisp-compile 'st "D:/jackcad2024/STANDAR/standar.LSP"))
(if (/= (findfile "D:/jackcad2024/Runallstruct.LSP") nil)(vlisp-compile 'st "D:/jackcad2024/Runallstruct.LSP"))
(if (/= (findfile "D:/jackcad2024/Terjunan/Terjuntersier.LSP") nil)(vlisp-compile 'st "D:/jackcad2024/Terjunan/Terjuntersier.LSP"))
(if (/= (findfile "D:/jackcad2024/Terjunan/bacadataterjuntersier.LSP") nil)(vlisp-compile 'st "D:/jackcad2024/Terjunan/bacadataterjuntersier.LSP"))
(if (/= (findfile "D:/jackcad2024/Terjunan/bacadataterjuntegak.LSP") nil)(vlisp-compile 'st "D:/jackcad2024/Terjunan/bacadataterjuntegak.LSP"))
(if (/= (findfile "D:/jackcad2024/Terjunan/Terjuntegak.LSP") nil)(vlisp-compile 'st "D:/jackcad2024/Terjunan/Terjuntegak.LSP"))
(if (/= (findfile "D:/jackcad2024/Terjunan/bacadataterjunmiring.LSP") nil)(vlisp-compile 'st "D:/jackcad2024/Terjunan/bacadataterjunmiring.LSP"))
(if (/= (findfile "D:/jackcad2024/Terjunan/Terjunmiring.LSP") nil)(vlisp-compile 'st "D:/jackcad2024/Terjunan/Terjunmiring.LSP"))
(if (/= (findfile "D:/jackcad2024/Boks/bacadatabox.LSP") nil)(vlisp-compile 'st "D:/jackcad2024/Boks/bacadatabox.LSP"))
(if (/= (findfile "D:/jackcad2024/Boks/Boks.LSP") nil)(vlisp-compile 'st "D:/jackcad2024/Boks/Boks.LSP"))
(if (/= (findfile "D:/jackcad2024/simbg.LSP") nil)(vlisp-compile 'st "D:/jackcad2024/simbg.LSP"))
(if (/= (findfile "D:/jackcad2024/simde.LSP") nil)(vlisp-compile 'st "D:/jackcad2024/simde.LSP"))
(if (/= (findfile "D:/jackcad2024/activ.LSP") nil)(vlisp-compile 'st "D:/jackcad2024/activ.LSP"))
(if (/= (findfile "D:/jackcad2024/simtp.LSP") nil)(vlisp-compile 'st "D:/jackcad2024/simtp.LSP"))
(if (/= (findfile "D:/jackcad2024/inputpw.LSP") nil)(vlisp-compile 'st "D:/jackcad2024/inputpw.LSP"))
(if (/= (findfile "D:/jackcad2024/Topo/total.LSP") nil)(vlisp-compile 'st "D:/jackcad2024/Topo/total.LSP"))
(if (/= (findfile "D:/jackcad2024/Topo/BM.LSP") nil)(vlisp-compile 'st "D:/jackcad2024/Topo/BM.LSP"))
(if (/= (findfile "D:/jackcad2024/Topo/Runtopo.LSP") nil)(vlisp-compile 'st "D:/jackcad2024/Topo/Runtopo.LSP"))
(if (/= (findfile "D:/jackcad2024/Topo/cross.LSP") nil)(vlisp-compile 'st "D:/jackcad2024/Topo/cross.LSP"))
(if (/= (findfile "D:/jackcad2024/Topo/poligon.LSP") nil)(vlisp-compile 'st "D:/jackcad2024/Topo/poligon.LSP"))
(if (/= (findfile "D:/jackcad2024/subroutine/bacadefault.LSP") nil)(vlisp-compile 'st "D:/jackcad2024/subroutine/bacadefault.LSP"))
(if (/= (findfile "D:/jackcad2024/Long/pl1.LSP") nil)(vlisp-compile 'st "D:/jackcad2024/Long/pl1.LSP"))
(if (/= (findfile "D:/jackcad2024/Long/hitungan.LSP") nil)(vlisp-compile 'st "D:/jackcad2024/Long/hitungan.LSP"))
(if (/= (findfile "D:/jackcad2024/Long/tul-dim.LSP") nil)(vlisp-compile 'st "D:/jackcad2024/Long/tul-dim.LSP"))
(if (/= (findfile "D:/jackcad2024/Long/RE-DIM.LSP") nil)(vlisp-compile 'st "D:/jackcad2024/Long/RE-DIM.LSP"))
(if (/= (findfile "D:/jackcad2024/Long/DAT-EL.LSP") nil)(vlisp-compile 'st "D:/jackcad2024/Long/DAT-EL.LSP"))
(if (/= (findfile "D:/jackcad2024/Long/irrpro.LSP") nil)(vlisp-compile 'st "D:/jackcad2024/Long/irrpro.LSP"))
;;(if (/= (findfile "D:/jackcad2024/layout/layout.LSP") nil)(vlisp-compile 'st "D:/jackcad2024/layout/layout.LSP"))
(if (/= (findfile "D:/jackcad2024/arah.LSP") nil)(vlisp-compile 'st "D:/jackcad2024/arah.LSP"))
(if (/= (findfile "D:/jackcad2024/Lsp-lain/lain.LSP") nil)(vlisp-compile 'st "D:/jackcad2024/Lsp-lain/lain.LSP"))
(if (/= (findfile "D:/jackcad2024/Proyek.LSP") nil)(vlisp-compile 'st "D:/jackcad2024/Proyek.LSP"))
(if (/= (findfile "D:/jackcad2024/CROSS/CRpe.LSP") nil)(vlisp-compile 'st "D:/jackcad2024/CROSS/CRpe.LSP"))
(if (/= (findfile "D:/jackcad2024/CROSS/C-main.LSP") nil)(vlisp-compile 'st "D:/jackcad2024/CROSS/C-main.LSP"))
(if (/= (findfile "D:/jackcad2024/Topo/XYZ.LSP") nil)(vlisp-compile 'st "D:/jackcad2024/Topo/XYZ.LSP"))
(if (/= (findfile "D:/jackcad2024/Topo/T-set.LSP") nil)(vlisp-compile 'st "D:/jackcad2024/Topo/T-set.LSP"))
(if (/= (findfile "D:/jackcad2024/Topo/rubahdem.LSP") nil)(vlisp-compile 'st "D:/jackcad2024/Topo/rubahdem.LSP"))
(if (/= (findfile "D:/jackcad2024/Topo/PLB.LSP") nil)(vlisp-compile 'st "D:/jackcad2024/Topo/PLB.LSP"))
(if (/= (findfile "D:/jackcad2024/Topo/O-Sit.LSP") nil)(vlisp-compile 'st "D:/jackcad2024/Topo/O-Sit.LSP"))
(if (/= (findfile "D:/jackcad2024/Topo/KOPILAY.LSP") nil)(vlisp-compile 'st "D:/jackcad2024/Topo/KOPILAY.LSP"))
(if (/= (findfile "D:/jackcad2024/Topo/Kopi.LSP") nil)(vlisp-compile 'st "D:/jackcad2024/Topo/Kopi.LSP"))
(if (/= (findfile "D:/jackcad2024/Topo/Kop-bang.LSP") nil)(vlisp-compile 'st "D:/jackcad2024/Topo/Kop-bang.LSP"))
(if (/= (findfile "D:/jackcad2024/Topo/GRIDI.LSP") nil)(vlisp-compile 'st "D:/jackcad2024/Topo/GRIDI.LSP"))
(if (/= (findfile "D:/jackcad2024/Topo/gbbang.LSP") nil)(vlisp-compile 'st "D:/jackcad2024/Topo/gbbang.LSP"))
(if (/= (findfile "D:/jackcad2024/Topo/etb.LSP") nil)(vlisp-compile 'st "D:/jackcad2024/Topo/etb.LSP"))
(if (/= (findfile "D:/jackcad2024/Topo/drb.LSP") nil)(vlisp-compile 'st "D:/jackcad2024/Topo/drb.LSP"))
(if (/= (findfile "D:/jackcad2024/Topo/crosdem.LSP") nil)(vlisp-compile 'st "D:/jackcad2024/Topo/crosdem.LSP"))
(if (/= (findfile "D:/jackcad2024/Topo/crd.LSP") nil)(vlisp-compile 'st "D:/jackcad2024/Topo/crd.LSP"))
(if (/= (findfile "D:/jackcad2024/Topo/ANAK.LSP") nil)(vlisp-compile 'st "D:/jackcad2024/Topo/ANAK.LSP"))
(if (/= (findfile "D:/jackcad2024/Terjunan/sub/terjunt2.LSP") nil)(vlisp-compile 'st "D:/jackcad2024/Terjunan/sub/terjunt2.LSP"))
(if (/= (findfile "D:/jackcad2024/Terjunan/sub/terjunM2.LSP") nil)(vlisp-compile 'st "D:/jackcad2024/Terjunan/sub/terjunM2.LSP"))
(if (/= (findfile "D:/jackcad2024/Terjunan/sub/terjun2.LSP") nil)(vlisp-compile 'st "D:/jackcad2024/Terjunan/sub/terjun2.LSP"))
(if (/= (findfile "D:/jackcad2024/Terjunan/sub/longterjunt.LSP") nil)(vlisp-compile 'st "D:/jackcad2024/Terjunan/sub/longterjunt.LSP"))
(if (/= (findfile "D:/jackcad2024/Terjunan/sub/longterjunm.LSP") nil)(vlisp-compile 'st "D:/jackcad2024/Terjunan/sub/longterjunm.LSP"))
(if (/= (findfile "D:/jackcad2024/Terjunan/sub/longterjun.LSP") nil)(vlisp-compile 'st "D:/jackcad2024/Terjunan/sub/longterjun.LSP"))
(if (/= (findfile "D:/jackcad2024/Terjunan/sub/longsal.LSP") nil)(vlisp-compile 'st "D:/jackcad2024/Terjunan/sub/longsal.LSP"))
(if (/= (findfile "D:/jackcad2024/Terjunan/sub/denah-sal.LSP") nil)(vlisp-compile 'st "D:/jackcad2024/Terjunan/sub/denah-sal.LSP"))
(if (/= (findfile "D:/jackcad2024/Terjunan/sub/crosterjunt.LSP") nil)(vlisp-compile 'st "D:/jackcad2024/Terjunan/sub/crosterjunt.LSP"))
(if (/= (findfile "D:/jackcad2024/Terjunan/sub/crosterjunm.LSP") nil)(vlisp-compile 'st "D:/jackcad2024/Terjunan/sub/crosterjunm.LSP"))
(if (/= (findfile "D:/jackcad2024/Terjunan/sub/crosterjun.LSP") nil)(vlisp-compile 'st "D:/jackcad2024/Terjunan/sub/crosterjun.LSP"))
(if (/= (findfile "D:/jackcad2024/Terjunan/BACA-DATmiring.LSP") nil)(vlisp-compile 'st "D:/jackcad2024/Terjunan/BACA-DATmiring.LSP"))
(if (/= (findfile "D:/jackcad2024/subroutine/bangunan/longsal.LSP") nil)(vlisp-compile 'st "D:/jackcad2024/subroutine/bangunan/longsal.LSP"))
(if (/= (findfile "D:/jackcad2024/subroutine/bangunan/crosssaluran.LSP") nil)(vlisp-compile 'st "D:/jackcad2024/subroutine/bangunan/crosssaluran.LSP"))
(if (/= (findfile "D:/jackcad2024/subroutine/bangunan/crossal2.LSP") nil)(vlisp-compile 'st "D:/jackcad2024/subroutine/bangunan/crossal2.LSP"))
(if (/= (findfile "D:/jackcad2024/subroutine/skalasituasi.LSP") nil)(vlisp-compile 'st "D:/jackcad2024/subroutine/skalasituasi.LSP"))
(if (/= (findfile "D:/jackcad2024/subroutine/lokasijudul.LSP") nil)(vlisp-compile 'st "D:/jackcad2024/subroutine/lokasijudul.LSP"))
(if (/= (findfile "D:/jackcad2024/subroutine/formprogrambaru.LSP") nil)(vlisp-compile 'st "D:/jackcad2024/subroutine/formprogrambaru.LSP"))
(if (/= (findfile "D:/jackcad2024/subroutine/cetakgambar.LSP") nil)(vlisp-compile 'st "D:/jackcad2024/subroutine/cetakgambar.LSP"))
(if (/= (findfile "D:/jackcad2024/subroutine/ba_da.LSP") nil)(vlisp-compile 'st "D:/jackcad2024/subroutine/ba_da.LSP"))
(if (/= (findfile "D:/jackcad2024/subroutine/bacanamaproyek.LSP") nil)(vlisp-compile 'st "D:/jackcad2024/subroutine/bacanamaproyek.LSP"))
(if (/= (findfile "D:/jackcad2024/subroutine/awalprogram.LSP") nil)(vlisp-compile 'st "D:/jackcad2024/subroutine/awalprogram.LSP"))
(if (/= (findfile "D:/jackcad2024/Sadap/sub/Denah/Pompa.LSP") nil)(vlisp-compile 'st "D:/jackcad2024/Sadap/sub/Denah/Pompa.LSP"))
(if (/= (findfile "D:/jackcad2024/Sadap/sub/Denah/Gorong.LSP") nil)(vlisp-compile 'st "D:/jackcad2024/Sadap/sub/Denah/Gorong.LSP"))
(if (/= (findfile "D:/jackcad2024/Sadap/sub/Denah/Dnsal.LSP") nil)(vlisp-compile 'st "D:/jackcad2024/Sadap/sub/Denah/Dnsal.LSP"))
(if (/= (findfile "D:/jackcad2024/Sadap/sub/Denah/Ambang.LSP") nil)(vlisp-compile 'st "D:/jackcad2024/Sadap/sub/Denah/Ambang.LSP"))
(if (/= (findfile "D:/jackcad2024/Sadap/sub/simbolair.LSP") nil)(vlisp-compile 'st "D:/jackcad2024/Sadap/sub/simbolair.LSP"))
(if (/= (findfile "D:/jackcad2024/Sadap/sub/longsambungan.LSP") nil)(vlisp-compile 'st "D:/jackcad2024/Sadap/sub/longsambungan.LSP"))
(if (/= (findfile "D:/jackcad2024/Sadap/sub/longsaluran.LSP") nil)(vlisp-compile 'st "D:/jackcad2024/Sadap/sub/longsaluran.LSP"))
(if (/= (findfile "D:/jackcad2024/Sadap/sub/longpompa.LSP") nil)(vlisp-compile 'st "D:/jackcad2024/Sadap/sub/longpompa.LSP"))
(if (/= (findfile "D:/jackcad2024/Sadap/sub/longbelok.LSP") nil)(vlisp-compile 'st "D:/jackcad2024/Sadap/sub/longbelok.LSP"))
(if (/= (findfile "D:/jackcad2024/Sadap/sub/inmir.LSP") nil)(vlisp-compile 'st "D:/jackcad2024/Sadap/sub/inmir.LSP"))
(if (/= (findfile "D:/jackcad2024/Sadap/sub/crospompa.LSP") nil)(vlisp-compile 'st "D:/jackcad2024/Sadap/sub/crospompa.LSP"))
(if (/= (findfile "D:/jackcad2024/Sadap/Ukur.LSP") nil)(vlisp-compile 'st "D:/jackcad2024/Sadap/Ukur.LSP"))
(if (/= (findfile "D:/jackcad2024/Sadap/Terjun.LSP") nil)(vlisp-compile 'st "D:/jackcad2024/Sadap/Terjun.LSP"))
(if (/= (findfile "D:/jackcad2024/Sadap/Sadap.LSP") nil)(vlisp-compile 'st "D:/jackcad2024/Sadap/Sadap.LSP"))
(if (/= (findfile "D:/jackcad2024/Sadap/BACA-DAT.LSP") nil)(vlisp-compile 'st "D:/jackcad2024/Sadap/BACA-DAT.LSP"))
(if (/= (findfile "D:/jackcad2024/Lsp-lain/RM.LSP") nil)(vlisp-compile 'st "D:/jackcad2024/Lsp-lain/RM.LSP"))
(if (/= (findfile "D:/jackcad2024/Long/Trase2.LSP") nil)(vlisp-compile 'st "D:/jackcad2024/Long/Trase2.LSP"))
(if (/= (findfile "D:/jackcad2024/Long/Trase.LSP") nil)(vlisp-compile 'st "D:/jackcad2024/Long/Trase.LSP"))
(if (/= (findfile "D:/jackcad2024/Long/O-long.LSP") nil)(vlisp-compile 'st "D:/jackcad2024/Long/O-long.LSP"))
(if (/= (findfile "D:/jackcad2024/Long/Ld-set.LSP") nil)(vlisp-compile 'st "D:/jackcad2024/Long/Ld-set.LSP"))
(if (/= (findfile "D:/jackcad2024/Long/ins-bgn.LSP") nil)(vlisp-compile 'st "D:/jackcad2024/Long/ins-bgn.LSP"))
(if (/= (findfile "D:/jackcad2024/Long/grs-renc.LSP") nil)(vlisp-compile 'st "D:/jackcad2024/Long/grs-renc.LSP"))
(if (/= (findfile "D:/jackcad2024/Long/GRS-RENC-step.LSP") nil)(vlisp-compile 'st "D:/jackcad2024/Long/GRS-RENC-step.LSP"))
(if (/= (findfile "D:/jackcad2024/CROSS/tnh-as.LSP") nil)(vlisp-compile 'st "D:/jackcad2024/CROSS/tnh-as.LSP"))
;;(if (/= (findfile "D:/jackcad2024/CROSS/Skatul.LSP") nil)(vlisp-compile 'st "D:/jackcad2024/CROSS/Skatul.LSP"))
(if (/= (findfile "D:/jackcad2024/CROSS/sal-renc.LSP") nil)(vlisp-compile 'st "D:/jackcad2024/CROSS/sal-renc.LSP"))
(if (/= (findfile "D:/jackcad2024/CROSS/SAL-RENC-tn.LSP") nil)(vlisp-compile 'st "D:/jackcad2024/CROSS/SAL-RENC-tn.LSP"))
(if (/= (findfile "D:/jackcad2024/CROSS/SAL-RENC-step.LSP") nil)(vlisp-compile 'st "D:/jackcad2024/CROSS/SAL-RENC-step.LSP"))
(if (/= (findfile "D:/jackcad2024/CROSS/O-cros.LSP") nil)(vlisp-compile 'st "D:/jackcad2024/CROSS/O-cros.LSP"))
(if (/= (findfile "D:/jackcad2024/CROSS/NC.LSP") nil)(vlisp-compile 'st "D:/jackcad2024/CROSS/NC.LSP"))
(if (/= (findfile "D:/jackcad2024/CROSS/bat-bebas.LSP") nil)(vlisp-compile 'st "D:/jackcad2024/CROSS/bat-bebas.LSP"))
(if (/= (findfile "D:/jackcad2024/Boks/sub/Sal6c.LSP") nil)(vlisp-compile 'st "D:/jackcad2024/Boks/sub/Sal6c.LSP"))
(if (/= (findfile "D:/jackcad2024/Boks/sub/Sal6b.LSP") nil)(vlisp-compile 'st "D:/jackcad2024/Boks/sub/Sal6b.LSP"))
(if (/= (findfile "D:/jackcad2024/Boks/sub/Sal6.LSP") nil)(vlisp-compile 'st "D:/jackcad2024/Boks/sub/Sal6.LSP"))
(if (/= (findfile "D:/jackcad2024/Boks/sub/Sal4i.LSP") nil)(vlisp-compile 'st "D:/jackcad2024/Boks/sub/Sal4i.LSP"))
(if (/= (findfile "D:/jackcad2024/Boks/sub/Sal4h.LSP") nil)(vlisp-compile 'st "D:/jackcad2024/Boks/sub/Sal4h.LSP"))
(if (/= (findfile "D:/jackcad2024/Boks/sub/Sal4g.LSP") nil)(vlisp-compile 'st "D:/jackcad2024/Boks/sub/Sal4g.LSP"))
(if (/= (findfile "D:/jackcad2024/Boks/sub/Sal4f.LSP") nil)(vlisp-compile 'st "D:/jackcad2024/Boks/sub/Sal4f.LSP"))
(if (/= (findfile "D:/jackcad2024/Boks/sub/Sal4e.LSP") nil)(vlisp-compile 'st "D:/jackcad2024/Boks/sub/Sal4e.LSP"))
(if (/= (findfile "D:/jackcad2024/Boks/sub/Sal4d.LSP") nil)(vlisp-compile 'st "D:/jackcad2024/Boks/sub/Sal4d.LSP"))
(if (/= (findfile "D:/jackcad2024/Boks/sub/Sal4c.LSP") nil)(vlisp-compile 'st "D:/jackcad2024/Boks/sub/Sal4c.LSP"))
(if (/= (findfile "D:/jackcad2024/Boks/sub/Sal4b.LSP") nil)(vlisp-compile 'st "D:/jackcad2024/Boks/sub/Sal4b.LSP"))
(if (/= (findfile "D:/jackcad2024/Boks/sub/Sal4.LSP") nil)(vlisp-compile 'st "D:/jackcad2024/Boks/sub/Sal4.LSP"))
(if (/= (findfile "D:/jackcad2024/Boks/sub/Sal2c.LSP") nil)(vlisp-compile 'st "D:/jackcad2024/Boks/sub/Sal2c.LSP"))
(if (/= (findfile "D:/jackcad2024/Boks/sub/Sal2b.LSP") nil)(vlisp-compile 'st "D:/jackcad2024/Boks/sub/Sal2b.LSP"))
(if (/= (findfile "D:/jackcad2024/Boks/sub/Sal2.LSP") nil)(vlisp-compile 'st "D:/jackcad2024/Boks/sub/Sal2.LSP"))
(if (/= (findfile "D:/jackcad2024/Boks/sub/Sal1.LSP") nil)(vlisp-compile 'st "D:/jackcad2024/Boks/sub/Sal1.LSP"))
(if (/= (findfile "D:/jackcad2024/Boks/sub/PML6bc.LSP") nil)(vlisp-compile 'st "D:/jackcad2024/Boks/sub/PML6bc.LSP"))
(if (/= (findfile "D:/jackcad2024/Boks/sub/PML6.LSP") nil)(vlisp-compile 'st "D:/jackcad2024/Boks/sub/PML6.LSP"))
(if (/= (findfile "D:/jackcad2024/Boks/sub/PML4fghi.LSP") nil)(vlisp-compile 'st "D:/jackcad2024/Boks/sub/PML4fghi.LSP"))
(if (/= (findfile "D:/jackcad2024/Boks/sub/PML4de.LSP") nil)(vlisp-compile 'st "D:/jackcad2024/Boks/sub/PML4de.LSP"))
(if (/= (findfile "D:/jackcad2024/Boks/sub/PML4BC.LSP") nil)(vlisp-compile 'st "D:/jackcad2024/Boks/sub/PML4BC.LSP"))
(if (/= (findfile "D:/jackcad2024/Boks/sub/PML4.LSP") nil)(vlisp-compile 'st "D:/jackcad2024/Boks/sub/PML4.LSP"))
(if (/= (findfile "D:/jackcad2024/Boks/sub/PML2bc.LSP") nil)(vlisp-compile 'st "D:/jackcad2024/Boks/sub/PML2bc.LSP"))
(if (/= (findfile "D:/jackcad2024/Boks/sub/PML2.LSP") nil)(vlisp-compile 'st "D:/jackcad2024/Boks/sub/PML2.LSP"))
(if (/= (findfile "D:/jackcad2024/Boks/sub/PMl1.LSP") nil)(vlisp-compile 'st "D:/jackcad2024/Boks/sub/PMl1.LSP"))
(if (/= (findfile "D:/jackcad2024/Boks/sub/pl3.LSP") nil)(vlisp-compile 'st "D:/jackcad2024/Boks/sub/pl3.LSP"))
(if (/= (findfile "D:/jackcad2024/Boks/sub/pl2.LSP") nil)(vlisp-compile 'st "D:/jackcad2024/Boks/sub/pl2.LSP"))
(if (/= (findfile "D:/jackcad2024/Boks/sub/pl1.LSP") nil)(vlisp-compile 'st "D:/jackcad2024/Boks/sub/pl1.LSP"))
(if (/= (findfile "D:/jackcad2024/Boks/sub/Longc2.LSP") nil)(vlisp-compile 'st "D:/jackcad2024/Boks/sub/Longc2.LSP"))
(if (/= (findfile "D:/jackcad2024/Boks/sub/Longc1.LSP") nil)(vlisp-compile 'st "D:/jackcad2024/Boks/sub/Longc1.LSP"))
(if (/= (findfile "D:/jackcad2024/Boks/sub/Longb5.LSP") nil)(vlisp-compile 'st "D:/jackcad2024/Boks/sub/Longb5.LSP"))
(if (/= (findfile "D:/jackcad2024/Boks/sub/Longb4.LSP") nil)(vlisp-compile 'st "D:/jackcad2024/Boks/sub/Longb4.LSP"))
(if (/= (findfile "D:/jackcad2024/Boks/sub/Longb3.LSP") nil)(vlisp-compile 'st "D:/jackcad2024/Boks/sub/Longb3.LSP"))
(if (/= (findfile "D:/jackcad2024/Boks/sub/Longb2.LSP") nil)(vlisp-compile 'st "D:/jackcad2024/Boks/sub/Longb2.LSP"))
(if (/= (findfile "D:/jackcad2024/Boks/sub/Longb1.LSP") nil)(vlisp-compile 'st "D:/jackcad2024/Boks/sub/Longb1.LSP"))
(if (/= (findfile "D:/jackcad2024/Boks/sub/Longa3.LSP") nil)(vlisp-compile 'st "D:/jackcad2024/Boks/sub/Longa3.LSP"))
(if (/= (findfile "D:/jackcad2024/Boks/sub/Longa2.LSP") nil)(vlisp-compile 'st "D:/jackcad2024/Boks/sub/Longa2.LSP"))
(if (/= (findfile "D:/jackcad2024/Boks/sub/Long1.LSP") nil)(vlisp-compile 'st "D:/jackcad2024/Boks/sub/Long1.LSP"))
(if (/= (findfile "D:/jackcad2024/bangunan/o-bangunan.LSP") nil)(vlisp-compile 'st "D:/jackcad2024/bangunan/o-bangunan.LSP"))
(if (/= (findfile "D:/jackcad2024/TU-SET.LSP") nil)(vlisp-compile 'st "D:/jackcad2024/TU-SET.LSP"))
(if (/= (findfile "D:/jackcad2024/RE-SET.LSP") nil)(vlisp-compile 'st "D:/jackcad2024/RE-SET.LSP"))
(if (/= (findfile "D:/jackcad2024/Pter.LSP") nil)(vlisp-compile 'st "D:/jackcad2024/Pter.LSP"))
(if (/= (findfile "D:/jackcad2024/Pkwar.LSP") nil)(vlisp-compile 'st "D:/jackcad2024/Pkwar.LSP"))
(if (/= (findfile "D:/jackcad2024/op-file.LSP") nil)(vlisp-compile 'st "D:/jackcad2024/op-file.LSP"))
(if (/= (findfile "D:/jackcad2024/Boks/sub/KOTAK.LSP") nil)(vlisp-compile 'st "D:/jackcad2024/Boks/sub/KOTAK.LSP"))
(if (/= (findfile "D:/jackcad2024/subroutine/arsirmiring.LSP") nil)(vlisp-compile 'st "D:/jackcad2024/subroutine/arsirmiring.LSP"))
(if (/= (findfile "D:/jackcad2024/subroutine/arsirtanah.LSP") nil)(vlisp-compile 'st "D:/jackcad2024/subroutine/arsirtanah.LSP"))
(if (/= (findfile "D:/jackcad2024/subroutine/hatchmiring.LSP") nil)(vlisp-compile 'st "D:/jackcad2024/subroutine/hatchmiring.LSP"))
(if (/= (findfile "D:/jackcad2024/CROSS/re-dim.LSP") nil)(vlisp-compile 'st "D:/jackcad2024/CROSS/re-dim.LSP"))
(if (/= (findfile "D:/jackcad2024/CROSS/pasangan.LSP") nil)(vlisp-compile 'st "D:/jackcad2024/CROSS/pasangan.LSP"))
(if (/= (findfile "D:/jackcad2024/CROSS/car-lok.LSP") nil)(vlisp-compile 'st "D:/jackcad2024/CROSS/car-lok.LSP"))
(if (/= (findfile "D:/jackcad2024/Sadap/sub/crossal.LSP") nil)(vlisp-compile 'st "D:/jackcad2024/Sadap/sub/crossal.LSP"))
(if (/= (findfile "D:/jackcad2024/Sadap/sub/KO-TEK2.LSP") nil)(vlisp-compile 'st "D:/jackcad2024/Sadap/sub/KO-TEK2.LSP"))
(if (/= (findfile "D:/jackcad2024/Sadap/sub/BOQ/Boqsaluran.LSP") nil)(vlisp-compile 'st "D:/jackcad2024/Sadap/sub/BOQ/Boqsaluran.LSP"))
(if (/= (findfile "D:/jackcad2024/Sadap/sub/dimsal.LSP") nil)(vlisp-compile 'st "D:/jackcad2024/Sadap/sub/dimsal.LSP"))
(if (/= (findfile "D:/jackcad2024/subroutine/serialnumber.LSP") nil)(vlisp-compile 'st "D:/jackcad2024/subroutine/serialnumber.LSP"))
(if (/= (findfile "D:/jackcad2024/subroutine/snc.LSP") nil)(vlisp-compile 'st "D:/jackcad2024/subroutine/snc.LSP"))
(if (/= (findfile "D:/jackcad2024/subroutine/copyfolder.LSP") nil)(vlisp-compile 'st "D:/jackcad2024/subroutine/copyfolder.LSP"))
(if (/= (findfile "D:/jackcad2024/Sadap/RM2.LSP") nil)(vlisp-compile 'st "D:/jackcad2024/Sadap/RM2.LSP"))
(if (/= (findfile "D:/jackcad2024/Sadap/sub/crospintu.LSP") nil)(vlisp-compile 'st "D:/jackcad2024/Sadap/sub/crospintu.LSP"))
(if (/= (findfile "D:/jackcad2024/Sadap/sub/longpintu.LSP") nil)(vlisp-compile 'st "D:/jackcad2024/Sadap/sub/longpintu.LSP"))
(if (/= (findfile "D:/jackcad2024/Sadap/sub/longgorong.LSP") nil)(vlisp-compile 'st "D:/jackcad2024/Sadap/sub/longgorong.LSP"))
(if (/= (findfile "D:/jackcad2024/Sadap/sub/crosgorong.LSP") nil)(vlisp-compile 'st "D:/jackcad2024/Sadap/sub/crosgorong.LSP"))
(if (/= (findfile "D:/jackcad2024/Sadap/sub/longambang.LSP") nil)(vlisp-compile 'st "D:/jackcad2024/Sadap/sub/longambang.LSP"))
(if (/= (findfile "D:/jackcad2024/Sadap/sub/awalkotak.LSP") nil)(vlisp-compile 'st "D:/jackcad2024/Sadap/sub/awalkotak.LSP"))
(if (/= (findfile "D:/jackcad2024/Sadap/sub/crosambang.LSP") nil)(vlisp-compile 'st "D:/jackcad2024/Sadap/sub/crosambang.LSP"))
(if (/= (findfile "D:/jackcad2024/subroutine/TeksDimensi.LSP") nil)(vlisp-compile 'st "D:/jackcad2024/subroutine/TeksDimensi.LSP"))
(if (/= (findfile "D:/jackcad2024/subroutine/settinghuruf.LSP") nil)(vlisp-compile 'st "D:/jackcad2024/subroutine/settinghuruf.LSP"))
(if (/= (findfile "D:/jackcad2024/subroutine/teks-elevasi.LSP") nil)(vlisp-compile 'st "D:/jackcad2024/subroutine/teks-elevasi.LSP"))
(if (/= (findfile "D:/jackcad2024/Sadap/sub/T-E.LSP") nil)(vlisp-compile 'st "D:/jackcad2024/Sadap/sub/T-E.LSP"))
(if (/= (findfile "D:/jackcad2024/Sadap/sub/sdbulat.LSP") nil)(vlisp-compile 'st "D:/jackcad2024/Sadap/sub/sdbulat.LSP"))
(if (/= (findfile "D:/jackcad2024/Sadap/sub/belno.LSP") nil)(vlisp-compile 'st "D:/jackcad2024/Sadap/sub/belno.LSP"))
(if (/= (findfile "D:/jackcad2024/Sadap/sub/MR1a.LSP") nil)(vlisp-compile 'st "D:/jackcad2024/Sadap/sub/MR1a.LSP"))
(if (/= (findfile "D:/jackcad2024/Sadap/sub/awalsdakhir.LSP") nil)(vlisp-compile 'st "D:/jackcad2024/Sadap/sub/awalsdakhir.LSP"))
(if (/= (findfile "D:/jackcad2024/Sadap/sub/settingsaluranawal.LSP") nil)(vlisp-compile 'st "D:/jackcad2024/Sadap/sub/settingsaluranawal.LSP"))
(if (/= (findfile "D:/jackcad2024/Sadap/sub/settingsaluranakhir.LSP") nil)(vlisp-compile 'st "D:/jackcad2024/Sadap/sub/settingsaluranakhir.LSP"))
(if (/= (findfile "D:/jackcad2024/Sadap/sub/dimlama.LSP") nil)(vlisp-compile 'st "D:/jackcad2024/Sadap/sub/dimlama.LSP"))
(if (/= (findfile "D:/jackcad2024/Long/tul-leng.LSP") nil)(vlisp-compile 'st "D:/jackcad2024/Long/tul-leng.LSP"))
(if (/= (findfile "D:/jackcad2024/Long/da-long.LSP") nil)(vlisp-compile 'st "D:/jackcad2024/Long/da-long.LSP"))
(if (/= (findfile "D:/jackcad2024/Long/FKURVA.LSP") nil)(vlisp-compile 'st "D:/jackcad2024/Long/FKURVA.LSP"))
(if (/= (findfile "D:/jackcad2024/CROSS/te-ja.LSP") nil)(vlisp-compile 'st "D:/jackcad2024/CROSS/te-ja.LSP"))
(if (/= (findfile "D:/jackcad2024/CROSS/aturc.LSP") nil)(vlisp-compile 'st "D:/jackcad2024/CROSS/aturc.LSP"))
(if (/= (findfile "D:/jackcad2024/CROSS/tul-dim.LSP") nil)(vlisp-compile 'st "D:/jackcad2024/CROSS/tul-dim.LSP"))
(if (/= (findfile "D:/jackcad2024/CROSS/TUL-DIM-step.LSP") nil)(vlisp-compile 'st "D:/jackcad2024/CROSS/TUL-DIM-step.LSP"))
(if (/= (findfile "D:/jackcad2024/CROSS/tul-datpat.LSP") nil)(vlisp-compile 'st "D:/jackcad2024/CROSS/tul-datpat.LSP"))
(if (/= (findfile "D:/jackcad2024/CROSS/T-E.LSP") nil)(vlisp-compile 'st "D:/jackcad2024/CROSS/T-E.LSP"))
(if (/= (findfile "D:/jackcad2024/CROSS/jalan.LSP") nil)(vlisp-compile 'st "D:/jackcad2024/CROSS/jalan.LSP"))
(if (/= (findfile "D:/jackcad2024/CROSS/gam.LSP") nil)(vlisp-compile 'st "D:/jackcad2024/CROSS/gam.LSP"))
(if (/= (findfile "D:/jackcad2024/Long/TUL-DAT.LSP") nil)(vlisp-compile 'st "D:/jackcad2024/Long/TUL-DAT.LSP"))
(if (/= (findfile "D:/jackcad2024/Long/TUL-DAT-step.LSP") nil)(vlisp-compile 'st "D:/jackcad2024/Long/TUL-DAT-step.LSP"))
(if (/= (findfile "D:/jackcad2024/Long/SKALA-V.LSP") nil)(vlisp-compile 'st "D:/jackcad2024/Long/SKALA-V.LSP"))
(if (/= (findfile "D:/jackcad2024/Long/hektom.LSP") nil)(vlisp-compile 'st "D:/jackcad2024/Long/hektom.LSP"))
(if (/= (findfile "D:/jackcad2024/Long/TUL-DIM-step.LSP") nil)(vlisp-compile 'st "D:/jackcad2024/Long/TUL-DIM-step.LSP"))
(if (/= (findfile "D:/jackcad2024/Long/D-C2.LSP") nil)(vlisp-compile 'st "D:/jackcad2024/Long/D-C2.LSP"))
(if (/= (findfile "D:/jackcad2024/Long/D-C1.LSP") nil)(vlisp-compile 'st "D:/jackcad2024/Long/D-C1.LSP"))
(if (/= (findfile "D:/jackcad2024/Long/DIMDRAIN.LSP") nil)(vlisp-compile 'st "D:/jackcad2024/Long/DIMDRAIN.LSP"))
(if (/= (findfile "D:/jackcad2024/Long/DIMCANAL.LSP") nil)(vlisp-compile 'st "D:/jackcad2024/Long/DIMCANAL.LSP"))
(if (/= (findfile "D:/jackcad2024/bangunan/aturBangunan.LSP") nil)(vlisp-compile 'st "D:/jackcad2024/bangunan/aturBangunan.LSP"))
(if (/= (findfile "D:/jackcad2024/Topo/Bacadatasituasi.LSP") nil)(vlisp-compile 'st "D:/jackcad2024/Topo/Bacadatasituasi.LSP"))
(if (/= (findfile "D:/jackcad2024/Topo/aturS.LSP") nil)(vlisp-compile 'st "D:/jackcad2024/Topo/aturS.LSP"))
(if (/= (findfile "D:/jackcad2024/subroutine/setqp.LSP") nil)(vlisp-compile 'st "D:/jackcad2024/subroutine/setqp.LSP"))
(if (/= (findfile "D:/jackcad2024/subroutine/daftarautolip.LSP") nil)(vlisp-compile 'st "D:/jackcad2024/subroutine/daftarautolip.LSP"))
(if (/= (findfile "D:/jackcad2024/CROSS/warna.LSP") nil)(vlisp-compile 'st "D:/jackcad2024/CROSS/warna.LSP"))
(if (/= (findfile "D:/jackcad2024/subroutine/bangunan/tip-PAS.LSP") nil)(vlisp-compile 'st "D:/jackcad2024/subroutine/bangunan/tip-PAS.LSP"))
(if (/= (findfile "D:/jackcad2024/arsir4.LSP") nil)(vlisp-compile 'st "D:/jackcad2024/arsir4.LSP"))
(if (/= (findfile "D:/jackcad2024/Terjunan/sub/KO-TEK.LSP") nil)(vlisp-compile 'st "D:/jackcad2024/Terjunan/sub/KO-TEK.LSP"))
(if (/= (findfile "D:/jackcad2024/inisial.LSP") nil)(vlisp-compile 'st "D:/jackcad2024/inisial.LSP"))
(if (/= (findfile "D:/jackcad2024/subroutine/inisial.LSP") nil)(vlisp-compile 'st "D:/jackcad2024/subroutine/inisial.LSP"))
;;;(if (/= (findfile "D:/jackcad2024/subroutine/rubahukuranhuruf.LSP") nil)(vlisp-compile 'st "D:/jackcad2024/subroutine/rubahukuranhuruf.LSP"))
(if (/= (findfile "D:/jackcad2024/subroutine/rubahelevasi.LSP") nil)(vlisp-compile 'st "D:/jackcad2024/subroutine/rubahelevasi.LSP"))
(if (/= (findfile "D:/jackcad2024/subroutine/putartext.LSP") nil)(vlisp-compile 'st "D:/jackcad2024/subroutine/putartext.LSP"))
(if (/= (findfile "D:/jackcad2024/subroutine/bacadataformtab.LSP") nil)(vlisp-compile 'st "D:/jackcad2024/subroutine/bacadataformtab.LSP"))
(if (/= (findfile "D:/jackcad2024/subroutine/bacadataexcel.LSP") nil)(vlisp-compile 'st "D:/jackcad2024/subroutine/bacadataexcel.LSP"))
(if (/= (findfile "D:/jackcad2024/subroutine/azimuth.LSP") nil)(vlisp-compile 'st "D:/jackcad2024/subroutine/azimuth.LSP"))
(if (/= (findfile "D:/jackcad2024/subroutine/bacalokjudul.LSP") nil)(vlisp-compile 'st "D:/jackcad2024/subroutine/bacalokjudul.LSP"))
(if (/= (findfile "D:/jackcad2024/subroutine/bangunan/Kotakdimensi.LSP") nil)(vlisp-compile 'st "D:/jackcad2024/subroutine/bangunan/Kotakdimensi.LSP"))
(if (/= (findfile "D:/jackcad2024/Boks/sub/KO-TEK.LSP") nil)(vlisp-compile 'st "D:/jackcad2024/Boks/sub/KO-TEK.LSP"))
(if (/= (findfile "D:/jackcad2024/subroutine/Browsefolder.LSP") nil)(vlisp-compile 'st "D:/jackcad2024/subroutine/Browsefolder.LSP"))
(if (/= (findfile "D:/jackcad2024/CROSS/re-fi.LSP") nil)(vlisp-compile 'st "D:/jackcad2024/CROSS/re-fi.LSP"))
(if (/= (findfile "D:/jackcad2024/Long/tip-PAS.LSP") nil)(vlisp-compile 'st "D:/jackcad2024/Long/tip-PAS.LSP"))
;;(if (/= (findfile "D:/jackcad2024/CROSS/Skat_l.LSP") nil)(vlisp-compile 'st "D:/jackcad2024/CROSS/Skat_l.LSP"))
(if (/= (findfile "D:/jackcad2024/Sadap/sub/BOQ/boqpompa.LSP") nil)(vlisp-compile 'st "D:/jackcad2024/Sadap/sub/BOQ/boqpompa.LSP"))
(if (/= (findfile "D:/jackcad2024/Sadap/sub/BOQ/boqambang.LSP") nil)(vlisp-compile 'st "D:/jackcad2024/Sadap/sub/BOQ/boqambang.LSP"))
(if (/= (findfile "D:/jackcad2024/Sadap/sub/BOQ/boqgorong.LSP") nil)(vlisp-compile 'st "D:/jackcad2024/Sadap/sub/BOQ/boqgorong.LSP"))
(if (/= (findfile "D:/jackcad2024/Sadap/sub/BOQ/boqsambungan.LSP") nil)(vlisp-compile 'st "D:/jackcad2024/Sadap/sub/BOQ/boqsambungan.LSP"))
(if (/= (findfile "D:/jackcad2024/Sadap/sub/BOQ/boqpintu.LSP") nil)(vlisp-compile 'st "D:/jackcad2024/Sadap/sub/BOQ/boqpintu.LSP"))
(if (/= (findfile "D:/jackcad2024/Sadap/sub/BOQ/boqbelokan.LSP") nil)(vlisp-compile 'st "D:/jackcad2024/Sadap/sub/BOQ/boqbelokan.LSP"))
(if (/= (findfile "D:/jackcad2024/Sadap/sub/setlay.LSP") nil)(vlisp-compile 'st "D:/jackcad2024/Sadap/sub/setlay.LSP"))
(if (/= (findfile "D:/jackcad2024/Sadap/sub/Denah/Pintu.LSP") nil)(vlisp-compile 'st "D:/jackcad2024/Sadap/sub/Denah/Pintu.LSP"))
(if (/= (findfile "D:/jackcad2024/Sadap/sub/koperup.LSP") nil)(vlisp-compile 'st "D:/jackcad2024/Sadap/sub/koperup.LSP"))
(if (/= (findfile "D:/jackcad2024/Sadap/carilokasi.LSP") nil)(vlisp-compile 'st "D:/jackcad2024/Sadap/carilokasi.LSP"))
(if (/= (findfile "D:/jackcad2024/Sadap/sub/Denah/Dnbelok.LSP") nil)(vlisp-compile 'st "D:/jackcad2024/Sadap/sub/Denah/Dnbelok.LSP"))
(if (/= (findfile "D:/jackcad2024/Sadap/sub/Denah/sambungan.LSP") nil)(vlisp-compile 'st "D:/jackcad2024/Sadap/sub/Denah/sambungan.LSP"))
(if (/= (findfile "D:/jackcad2024/Sadap/sub/Dnpier.LSP") nil)(vlisp-compile 'st "D:/jackcad2024/Sadap/sub/Dnpier.LSP"))
(if (/= (findfile "D:/jackcad2024/Sadap/sub/Dnpusat.LSP") nil)(vlisp-compile 'st "D:/jackcad2024/Sadap/sub/Dnpusat.LSP"))
(if (/= (findfile "D:/jackcad2024/Sadap/sub/DtRd.LSP") nil)(vlisp-compile 'st "D:/jackcad2024/Sadap/sub/DtRd.LSP"))
(if (/= (findfile "D:/jackcad2024/Sadap/sub/RM4.LSP") nil)(vlisp-compile 'st "D:/jackcad2024/Sadap/sub/RM4.LSP"))
(if (/= (findfile "D:/jackcad2024/Sadap/sub/MR1.LSP") nil)(vlisp-compile 'st "D:/jackcad2024/Sadap/sub/MR1.LSP"))
(if (/= (findfile "D:/jackcad2024/Sadap/sub/Dnpin.LSP") nil)(vlisp-compile 'st "D:/jackcad2024/Sadap/sub/Dnpin.LSP"))
(if (/= (findfile "D:/jackcad2024/Sadap/sub/MR4.LSP") nil)(vlisp-compile 'st "D:/jackcad2024/Sadap/sub/MR4.LSP"))
(if (/= (findfile "D:/jackcad2024/Sadap/sub/Melintang/jenislining.LSP") nil)(vlisp-compile 'st "D:/jackcad2024/Sadap/sub/Melintang/jenislining.LSP"))
(if (/= (findfile "D:/jackcad2024/Sadap/nl.LSP") nil)(vlisp-compile 'st "D:/jackcad2024/Sadap/nl.LSP"))
(if (/= (findfile "D:/jackcad2024/nilai.LSP") nil)(vlisp-compile 'st "D:/jackcad2024/nilai.LSP"))
(if (/= (findfile "D:/jackcad2024/tam+.LSP") nil)(vlisp-compile 'st "D:/jackcad2024/tam+.LSP"))
(if (/= (findfile "D:/jackcad2024/Lsp-lain/lng.LSP") nil)(vlisp-compile 'st "D:/jackcad2024/Lsp-lain/lng.LSP"))
(if (/= (findfile "D:/jackcad2024/contoh/Setting/ATURL.LSP") nil)(vlisp-compile 'st "D:/jackcad2024/contoh/Setting/ATURL.LSP"))
(if (/= (findfile "D:/jackcad2024/Formkosong/Setting/ATURL.LSP") nil)(vlisp-compile 'st "D:/jackcad2024/Formkosong/Setting/ATURL.LSP"))
(if (/= (findfile "D:/jackcad2024/contoh/Setting/ATURC.LSP") nil)(vlisp-compile 'st "D:/jackcad2024/contoh/Setting/ATURC.LSP"))
(if (/= (findfile "D:/jackcad2024/Formkosong/Setting/ATURC.LSP") nil)(vlisp-compile 'st "D:/jackcad2024/Formkosong/Setting/ATURC.LSP"))
(if (/= (findfile "D:/jackcad2024/rubahdat.LSP") nil)(vlisp-compile 'st "D:/jackcad2024/rubahdat.LSP"))
(if (/= (findfile "D:/jackcad2024/Terjunan/sub/RM1.LSP") nil)(vlisp-compile 'st "D:/jackcad2024/Terjunan/sub/RM1.LSP"))
(if (/= (findfile "D:/jackcad2024/Boks/sub/KOPER.LSP") nil)(vlisp-compile 'st "D:/jackcad2024/Boks/sub/KOPER.LSP"))
(if (/= (findfile "D:/jackcad2024/Boks/sub/RM.LSP") nil)(vlisp-compile 'st "D:/jackcad2024/Boks/sub/RM.LSP"))
(if (/= (findfile "D:/jackcad2024/Boks/sub/RM2.LSP") nil)(vlisp-compile 'st "D:/jackcad2024/Boks/sub/RM2.LSP"))
(if (/= (findfile "D:/jackcad2024/CROSS/C-drain.LSP") nil)(vlisp-compile 'st "D:/jackcad2024/CROSS/C-drain.LSP"))
(if (/= (findfile "D:/jackcad2024/CROSS/C-ter.LSP") nil)(vlisp-compile 'st "D:/jackcad2024/CROSS/C-ter.LSP"))
(if (/= (findfile "D:/jackcad2024/CROSS/CAR-LOK-step.LSP") nil)(vlisp-compile 'st "D:/jackcad2024/CROSS/CAR-LOK-step.LSP"))
(if (/= (findfile "D:/jackcad2024/CROSS/centerline.LSP") nil)(vlisp-compile 'st "D:/jackcad2024/CROSS/centerline.LSP"))
(if (/= (findfile "D:/jackcad2024/CROSS/GALTIM.LSP") nil)(vlisp-compile 'st "D:/jackcad2024/CROSS/GALTIM.LSP"))
(if (/= (findfile "D:/jackcad2024/CROSS/GRS-TN.LSP") nil)(vlisp-compile 'st "D:/jackcad2024/CROSS/GRS-TN.LSP"))
(if (/= (findfile "D:/jackcad2024/CROSS/Ins-das.LSP") nil)(vlisp-compile 'st "D:/jackcad2024/CROSS/Ins-das.LSP"))
(if (/= (findfile "D:/jackcad2024/CROSS/KUPAS.LSP") nil)(vlisp-compile 'st "D:/jackcad2024/CROSS/KUPAS.LSP"))
(if (/= (findfile "D:/jackcad2024/CROSS/KUPASAN.LSP") nil)(vlisp-compile 'st "D:/jackcad2024/CROSS/KUPASAN.LSP"))
(if (/= (findfile "D:/jackcad2024/CROSS/LUASAN.LSP") nil)(vlisp-compile 'st "D:/jackcad2024/CROSS/LUASAN.LSP"))
(if (/= (findfile "D:/jackcad2024/CROSS/POTONG.LSP") nil)(vlisp-compile 'st "D:/jackcad2024/CROSS/POTONG.LSP"))
(if (/= (findfile "D:/jackcad2024/CROSS/POTONG2.LSP") nil)(vlisp-compile 'st "D:/jackcad2024/CROSS/POTONG2.LSP"))
(if (/= (findfile "D:/jackcad2024/CROSS/RE-DIM-step.LSP") nil)(vlisp-compile 'st "D:/jackcad2024/CROSS/RE-DIM-step.LSP"))
(if (/= (findfile "D:/jackcad2024/CROSS/RU-DAT.LSP") nil)(vlisp-compile 'st "D:/jackcad2024/CROSS/RU-DAT.LSP"))
(if (/= (findfile "D:/jackcad2024/CROSS/SET-JRK.LSP") nil)(vlisp-compile 'st "D:/jackcad2024/CROSS/SET-JRK.LSP"))
(if (/= (findfile "D:/jackcad2024/CROSS/Set-ltk.LSP") nil)(vlisp-compile 'st "D:/jackcad2024/CROSS/Set-ltk.LSP"))
(if (/= (findfile "D:/jackcad2024/Long/1LEMBAR.LSP") nil)(vlisp-compile 'st "D:/jackcad2024/Long/1LEMBAR.LSP"))
(if (/= (findfile "D:/jackcad2024/Long/ATURL.LSP") nil)(vlisp-compile 'st "D:/jackcad2024/Long/ATURL.LSP"))
(if (/= (findfile "D:/jackcad2024/Long/DA-LENG.LSP") nil)(vlisp-compile 'st "D:/jackcad2024/Long/DA-LENG.LSP"))
(if (/= (findfile "D:/jackcad2024/Long/DA-LONG-step.LSP") nil)(vlisp-compile 'st "D:/jackcad2024/Long/DA-LONG-step.LSP"))
(if (/= (findfile "D:/jackcad2024/Long/DAMAXMIN.LSP") nil)(vlisp-compile 'st "D:/jackcad2024/Long/DAMAXMIN.LSP"))
(if (/= (findfile "D:/jackcad2024/Long/DAT-EL-step.LSP") nil)(vlisp-compile 'st "D:/jackcad2024/Long/DAT-EL-step.LSP"))
(if (/= (findfile "D:/jackcad2024/Long/DELTEXT.LSP") nil)(vlisp-compile 'st "D:/jackcad2024/Long/DELTEXT.LSP"))
(if (/= (findfile "D:/jackcad2024/Long/FGARIS.LSP") nil)(vlisp-compile 'st "D:/jackcad2024/Long/FGARIS.LSP"))
(if (/= (findfile "D:/jackcad2024/Long/FGARIS2.LSP") nil)(vlisp-compile 'st "D:/jackcad2024/Long/FGARIS2.LSP"))
(if (/= (findfile "D:/jackcad2024/Long/FKURVA2.LSP") nil)(vlisp-compile 'st "D:/jackcad2024/Long/FKURVA2.LSP"))
(if (/= (findfile "D:/jackcad2024/Long/Ins-kop.LSP") nil)(vlisp-compile 'st "D:/jackcad2024/Long/Ins-kop.LSP"))
(if (/= (findfile "D:/jackcad2024/Long/L-drain.LSP") nil)(vlisp-compile 'st "D:/jackcad2024/Long/L-drain.LSP"))
(if (/= (findfile "D:/jackcad2024/Long/L-main.LSP") nil)(vlisp-compile 'st "D:/jackcad2024/Long/L-main.LSP"))
(if (/= (findfile "D:/jackcad2024/Long/L-ter.LSP") nil)(vlisp-compile 'st "D:/jackcad2024/Long/L-ter.LSP"))
(if (/= (findfile "D:/jackcad2024/Long/RE-DIM-step.LSP") nil)(vlisp-compile 'st "D:/jackcad2024/Long/RE-DIM-step.LSP"))
(if (/= (findfile "D:/jackcad2024/Long/RE-DIM-stepL.LSP") nil)(vlisp-compile 'st "D:/jackcad2024/Long/RE-DIM-stepL.LSP"))
(if (/= (findfile "D:/jackcad2024/Long/RE-SDT.LSP") nil)(vlisp-compile 'st "D:/jackcad2024/Long/RE-SDT.LSP"))
(if (/= (findfile "D:/jackcad2024/Lsp-lain/RM2.LSP") nil)(vlisp-compile 'st "D:/jackcad2024/Lsp-lain/RM2.LSP"))
(if (/= (findfile "D:/jackcad2024/Sadap/RM.LSP") nil)(vlisp-compile 'st "D:/jackcad2024/Sadap/RM.LSP"))

(if (and (/= (findfile "D:/jackcad2024/Topo/stoe.LSP") nil)(/= (findfile "D:/jackcad2024/Topo/stoe.fas") nil))(vl-file-delete  "D:/jackcad2024/Topo/stoe.LSP"))
(if (and (/= (findfile "D:/jackcad2024/STANDAR/standar.LSP") nil)(/= (findfile "D:/jackcad2024/STANDAR/standar.fas") nil))(vl-file-delete  "D:/jackcad2024/STANDAR/standar.LSP"))
(if (and (/= (findfile "D:/jackcad2024/Runallstruct.lsp") nil)(/= (findfile "D:/jackcad2024/Runallstruct.fas") nil))(vl-file-delete  "D:/jackcad2024/Runallstruct.lsp"))
(if (and (/= (findfile "D:/jackcad2024/Terjunan/Terjuntersier.LSP") nil)(/= (findfile "D:/jackcad2024/Terjunan/Terjuntersier.fas") nil))(vl-file-delete  "D:/jackcad2024/Terjunan/Terjuntersier.LSP"))
(if (and (/= (findfile "D:/jackcad2024/Terjunan/bacadataterjuntersier.LSP") nil)(/= (findfile "D:/jackcad2024/Terjunan/bacadataterjuntersier.fas") nil))(vl-file-delete  "D:/jackcad2024/Terjunan/bacadataterjuntersier.LSP"))
(if (and (/= (findfile "D:/jackcad2024/Terjunan/bacadataterjuntegak.LSP") nil)(/= (findfile "D:/jackcad2024/Terjunan/bacadataterjuntegak.fas") nil))(vl-file-delete  "D:/jackcad2024/Terjunan/bacadataterjuntegak.LSP"))
(if (and (/= (findfile "D:/jackcad2024/Terjunan/Terjuntegak.LSP") nil)(/= (findfile "D:/jackcad2024/Terjunan/Terjuntegak.fas") nil))(vl-file-delete  "D:/jackcad2024/Terjunan/Terjuntegak.LSP"))
(if (and (/= (findfile "D:/jackcad2024/Terjunan/bacadataterjunmiring.LSP") nil)(/= (findfile "D:/jackcad2024/Terjunan/bacadataterjunmiring.fas") nil))(vl-file-delete  "D:/jackcad2024/Terjunan/bacadataterjunmiring.LSP"))
(if (and (/= (findfile "D:/jackcad2024/Terjunan/Terjunmiring.LSP") nil)(/= (findfile "D:/jackcad2024/Terjunan/Terjunmiring.fas") nil))(vl-file-delete  "D:/jackcad2024/Terjunan/Terjunmiring.LSP"))
(if (and (/= (findfile "D:/jackcad2024/Boks/bacadatabox.LSP") nil)(/= (findfile "D:/jackcad2024/Boks/bacadatabox.fas") nil))(vl-file-delete  "D:/jackcad2024/Boks/bacadatabox.LSP"))
(if (and (/= (findfile "D:/jackcad2024/Boks/Boks.lsp") nil)(/= (findfile "D:/jackcad2024/Boks/Boks.fas") nil))(vl-file-delete  "D:/jackcad2024/Boks/Boks.lsp"))
(if (and (/= (findfile "D:/jackcad2024/simbg.LSP") nil)(/= (findfile "D:/jackcad2024/simbg.fas") nil))(vl-file-delete  "D:/jackcad2024/simbg.LSP"))
(if (and (/= (findfile "D:/jackcad2024/simde.LSP") nil)(/= (findfile "D:/jackcad2024/simde.fas") nil))(vl-file-delete  "D:/jackcad2024/simde.LSP"))
(if (and (/= (findfile "D:/jackcad2024/activ.LSP") nil)(/= (findfile "D:/jackcad2024/activ.fas") nil))(vl-file-delete  "D:/jackcad2024/activ.LSP"))
(if (and (/= (findfile "D:/jackcad2024/simtp.LSP") nil)(/= (findfile "D:/jackcad2024/simtp.fas") nil))(vl-file-delete  "D:/jackcad2024/simtp.LSP"))
(if (and (/= (findfile "D:/jackcad2024/inputpw.LSP") nil)(/= (findfile "D:/jackcad2024/inputpw.fas") nil))(vl-file-delete  "D:/jackcad2024/inputpw.LSP"))
(if (and (/= (findfile "D:/jackcad2024/Topo/total.lsp") nil)(/= (findfile "D:/jackcad2024/Topo/total.fas") nil))(vl-file-delete  "D:/jackcad2024/Topo/total.lsp"))
(if (and (/= (findfile "D:/jackcad2024/Topo/BM.LSP") nil)(/= (findfile "D:/jackcad2024/Topo/BM.fas") nil))(vl-file-delete  "D:/jackcad2024/Topo/BM.LSP"))
(if (and (/= (findfile "D:/jackcad2024/Topo/Runtopo.lsp") nil)(/= (findfile "D:/jackcad2024/Topo/Runtopo.fas") nil))(vl-file-delete  "D:/jackcad2024/Topo/Runtopo.lsp"))
(if (and (/= (findfile "D:/jackcad2024/Topo/cross.LSP") nil)(/= (findfile "D:/jackcad2024/Topo/cross.fas") nil))(vl-file-delete  "D:/jackcad2024/Topo/cross.LSP"))
(if (and (/= (findfile "D:/jackcad2024/Topo/poligon.LSP") nil)(/= (findfile "D:/jackcad2024/Topo/poligon.fas") nil))(vl-file-delete  "D:/jackcad2024/Topo/poligon.LSP"))
(if (and (/= (findfile "D:/jackcad2024/subroutine/bacadefault.LSP") nil)(/= (findfile "D:/jackcad2024/subroutine/bacadefault.fas") nil))(vl-file-delete  "D:/jackcad2024/subroutine/bacadefault.LSP"))
(if (and (/= (findfile "D:/jackcad2024/Long/pl1.LSP") nil)(/= (findfile "D:/jackcad2024/Long/pl1.fas") nil))(vl-file-delete  "D:/jackcad2024/Long/pl1.LSP"))
(if (and (/= (findfile "D:/jackcad2024/Long/hitungan.LSP") nil)(/= (findfile "D:/jackcad2024/Long/hitungan.fas") nil))(vl-file-delete  "D:/jackcad2024/Long/hitungan.LSP"))
(if (and (/= (findfile "D:/jackcad2024/Long/tul-dim.LSP") nil)(/= (findfile "D:/jackcad2024/Long/tul-dim.fas") nil))(vl-file-delete  "D:/jackcad2024/Long/tul-dim.LSP"))
(if (and (/= (findfile "D:/jackcad2024/Long/RE-DIM.LSP") nil)(/= (findfile "D:/jackcad2024/Long/RE-DIM.fas") nil))(vl-file-delete  "D:/jackcad2024/Long/RE-DIM.LSP"))
(if (and (/= (findfile "D:/jackcad2024/Long/DAT-EL.LSP") nil)(/= (findfile "D:/jackcad2024/Long/DAT-EL.fas") nil))(vl-file-delete  "D:/jackcad2024/Long/DAT-EL.LSP"))
(if (and (/= (findfile "D:/jackcad2024/Long/irrpro.LSP") nil)(/= (findfile "D:/jackcad2024/Long/irrpro.fas") nil))(vl-file-delete  "D:/jackcad2024/Long/irrpro.LSP"))
;;(if (and (/= (findfile "D:/jackcad2024/layout/layout.LSP") nil)(/= (findfile "D:/jackcad2024/layout/layout.fas") nil))(vl-file-delete  "D:/jackcad2024/layout/layout.LSP"))
(if (and (/= (findfile "D:/jackcad2024/arah.lsp") nil)(/= (findfile "D:/jackcad2024/arah.fas") nil))(vl-file-delete  "D:/jackcad2024/arah.lsp"))
(if (and (/= (findfile "D:/jackcad2024/Lsp-lain/lain.LSP") nil)(/= (findfile "D:/jackcad2024/Lsp-lain/lain.fas") nil))(vl-file-delete  "D:/jackcad2024/Lsp-lain/lain.LSP"))
(if (and (/= (findfile "D:/jackcad2024/Proyek.LSP") nil)(/= (findfile "D:/jackcad2024/Proyek.fas") nil))(vl-file-delete  "D:/jackcad2024/Proyek.LSP"))
(if (and (/= (findfile "D:/jackcad2024/CROSS/CRpe.lsp") nil)(/= (findfile "D:/jackcad2024/CROSS/CRpe.fas") nil))(vl-file-delete  "D:/jackcad2024/CROSS/CRpe.lsp"))
(if (and (/= (findfile "D:/jackcad2024/CROSS/C-main.lsp") nil)(/= (findfile "D:/jackcad2024/CROSS/C-main.fas") nil))(vl-file-delete  "D:/jackcad2024/CROSS/C-main.lsp"))
(if (and (/= (findfile "D:/jackcad2024/Topo/XYZ.LSP") nil)(/= (findfile "D:/jackcad2024/Topo/XYZ.fas") nil))(vl-file-delete  "D:/jackcad2024/Topo/XYZ.LSP"))
(if (and (/= (findfile "D:/jackcad2024/Topo/T-set.lsp") nil)(/= (findfile "D:/jackcad2024/Topo/T-set.fas") nil))(vl-file-delete  "D:/jackcad2024/Topo/T-set.lsp"))
(if (and (/= (findfile "D:/jackcad2024/Topo/rubahdem.LSP") nil)(/= (findfile "D:/jackcad2024/Topo/rubahdem.fas") nil))(vl-file-delete  "D:/jackcad2024/Topo/rubahdem.LSP"))
(if (and (/= (findfile "D:/jackcad2024/Topo/PLB.LSP") nil)(/= (findfile "D:/jackcad2024/Topo/PLB.fas") nil))(vl-file-delete  "D:/jackcad2024/Topo/PLB.LSP"))
(if (and (/= (findfile "D:/jackcad2024/Topo/O-Sit.lsp") nil)(/= (findfile "D:/jackcad2024/Topo/O-Sit.fas") nil))(vl-file-delete  "D:/jackcad2024/Topo/O-Sit.lsp"))
(if (and (/= (findfile "D:/jackcad2024/Topo/KOPILAY.LSP") nil)(/= (findfile "D:/jackcad2024/Topo/KOPILAY.fas") nil))(vl-file-delete  "D:/jackcad2024/Topo/KOPILAY.LSP"))
(if (and (/= (findfile "D:/jackcad2024/Topo/Kopi.lsp") nil)(/= (findfile "D:/jackcad2024/Topo/Kopi.fas") nil))(vl-file-delete  "D:/jackcad2024/Topo/Kopi.lsp"))
(if (and (/= (findfile "D:/jackcad2024/Topo/Kop-bang.lsp") nil)(/= (findfile "D:/jackcad2024/Topo/Kop-bang.fas") nil))(vl-file-delete  "D:/jackcad2024/Topo/Kop-bang.lsp"))
(if (and (/= (findfile "D:/jackcad2024/Topo/GRIDI.LSP") nil)(/= (findfile "D:/jackcad2024/Topo/GRIDI.fas") nil))(vl-file-delete  "D:/jackcad2024/Topo/GRIDI.LSP"))
(if (and (/= (findfile "D:/jackcad2024/Topo/gbbang.LSP") nil)(/= (findfile "D:/jackcad2024/Topo/gbbang.fas") nil))(vl-file-delete  "D:/jackcad2024/Topo/gbbang.LSP"))
(if (and (/= (findfile "D:/jackcad2024/Topo/etb.LSP") nil)(/= (findfile "D:/jackcad2024/Topo/etb.fas") nil))(vl-file-delete  "D:/jackcad2024/Topo/etb.LSP"))
(if (and (/= (findfile "D:/jackcad2024/Topo/drb.LSP") nil)(/= (findfile "D:/jackcad2024/Topo/drb.fas") nil))(vl-file-delete  "D:/jackcad2024/Topo/drb.LSP"))
(if (and (/= (findfile "D:/jackcad2024/Topo/crosdem.LSP") nil)(/= (findfile "D:/jackcad2024/Topo/crosdem.fas") nil))(vl-file-delete  "D:/jackcad2024/Topo/crosdem.LSP"))
(if (and (/= (findfile "D:/jackcad2024/Topo/crd.LSP") nil)(/= (findfile "D:/jackcad2024/Topo/crd.fas") nil))(vl-file-delete  "D:/jackcad2024/Topo/crd.LSP"))
(if (and (/= (findfile "D:/jackcad2024/Topo/ANAK.LSP") nil)(/= (findfile "D:/jackcad2024/Topo/ANAK.fas") nil))(vl-file-delete  "D:/jackcad2024/Topo/ANAK.LSP"))
(if (and (/= (findfile "D:/jackcad2024/Terjunan/sub/terjunt2.LSP") nil)(/= (findfile "D:/jackcad2024/Terjunan/sub/terjunt2.fas") nil))(vl-file-delete  "D:/jackcad2024/Terjunan/sub/terjunt2.LSP"))
(if (and (/= (findfile "D:/jackcad2024/Terjunan/sub/terjunM2.LSP") nil)(/= (findfile "D:/jackcad2024/Terjunan/sub/terjunM2.fas") nil))(vl-file-delete  "D:/jackcad2024/Terjunan/sub/terjunM2.LSP"))
(if (and (/= (findfile "D:/jackcad2024/Terjunan/sub/terjun2.LSP") nil)(/= (findfile "D:/jackcad2024/Terjunan/sub/terjun2.fas") nil))(vl-file-delete  "D:/jackcad2024/Terjunan/sub/terjun2.LSP"))
(if (and (/= (findfile "D:/jackcad2024/Terjunan/sub/longterjunt.LSP") nil)(/= (findfile "D:/jackcad2024/Terjunan/sub/longterjunt.fas") nil))(vl-file-delete  "D:/jackcad2024/Terjunan/sub/longterjunt.LSP"))
(if (and (/= (findfile "D:/jackcad2024/Terjunan/sub/longterjunm.LSP") nil)(/= (findfile "D:/jackcad2024/Terjunan/sub/longterjunm.fas") nil))(vl-file-delete  "D:/jackcad2024/Terjunan/sub/longterjunm.LSP"))
(if (and (/= (findfile "D:/jackcad2024/Terjunan/sub/longterjun.LSP") nil)(/= (findfile "D:/jackcad2024/Terjunan/sub/longterjun.fas") nil))(vl-file-delete  "D:/jackcad2024/Terjunan/sub/longterjun.LSP"))
(if (and (/= (findfile "D:/jackcad2024/Terjunan/sub/longsal.LSP") nil)(/= (findfile "D:/jackcad2024/Terjunan/sub/longsal.fas") nil))(vl-file-delete  "D:/jackcad2024/Terjunan/sub/longsal.LSP"))
(if (and (/= (findfile "D:/jackcad2024/Terjunan/sub/denah-sal.LSP") nil)(/= (findfile "D:/jackcad2024/Terjunan/sub/denah-sal.fas") nil))(vl-file-delete  "D:/jackcad2024/Terjunan/sub/denah-sal.LSP"))
(if (and (/= (findfile "D:/jackcad2024/Terjunan/sub/crosterjunt.LSP") nil)(/= (findfile "D:/jackcad2024/Terjunan/sub/crosterjunt.fas") nil))(vl-file-delete  "D:/jackcad2024/Terjunan/sub/crosterjunt.LSP"))
(if (and (/= (findfile "D:/jackcad2024/Terjunan/sub/crosterjunm.LSP") nil)(/= (findfile "D:/jackcad2024/Terjunan/sub/crosterjunm.fas") nil))(vl-file-delete  "D:/jackcad2024/Terjunan/sub/crosterjunm.LSP"))
(if (and (/= (findfile "D:/jackcad2024/Terjunan/sub/crosterjun.LSP") nil)(/= (findfile "D:/jackcad2024/Terjunan/sub/crosterjun.fas") nil))(vl-file-delete  "D:/jackcad2024/Terjunan/sub/crosterjun.LSP"))
(if (and (/= (findfile "D:/jackcad2024/Terjunan/BACA-DATmiring.LSP") nil)(/= (findfile "D:/jackcad2024/Terjunan/BACA-DATmiring.fas") nil))(vl-file-delete  "D:/jackcad2024/Terjunan/BACA-DATmiring.LSP"))
(if (and (/= (findfile "D:/jackcad2024/subroutine/bangunan/longsal.LSP") nil)(/= (findfile "D:/jackcad2024/subroutine/bangunan/longsal.fas") nil))(vl-file-delete  "D:/jackcad2024/subroutine/bangunan/longsal.LSP"))
(if (and (/= (findfile "D:/jackcad2024/subroutine/bangunan/crosssaluran.LSP") nil)(/= (findfile "D:/jackcad2024/subroutine/bangunan/crosssaluran.fas") nil))(vl-file-delete  "D:/jackcad2024/subroutine/bangunan/crosssaluran.LSP"))
(if (and (/= (findfile "D:/jackcad2024/subroutine/bangunan/crossal2.LSP") nil)(/= (findfile "D:/jackcad2024/subroutine/bangunan/crossal2.fas") nil))(vl-file-delete  "D:/jackcad2024/subroutine/bangunan/crossal2.LSP"))
(if (and (/= (findfile "D:/jackcad2024/subroutine/skalasituasi.LSP") nil)(/= (findfile "D:/jackcad2024/subroutine/skalasituasi.fas") nil))(vl-file-delete  "D:/jackcad2024/subroutine/skalasituasi.LSP"))
(if (and (/= (findfile "D:/jackcad2024/subroutine/lokasijudul.LSP") nil)(/= (findfile "D:/jackcad2024/subroutine/lokasijudul.fas") nil))(vl-file-delete  "D:/jackcad2024/subroutine/lokasijudul.LSP"))
(if (and (/= (findfile "D:/jackcad2024/subroutine/formprogrambaru.lsp") nil)(/= (findfile "D:/jackcad2024/subroutine/formprogrambaru.fas") nil))(vl-file-delete  "D:/jackcad2024/subroutine/formprogrambaru.lsp"))
(if (and (/= (findfile "D:/jackcad2024/subroutine/cetakgambar.LSP") nil)(/= (findfile "D:/jackcad2024/subroutine/cetakgambar.fas") nil))(vl-file-delete  "D:/jackcad2024/subroutine/cetakgambar.LSP"))
(if (and (/= (findfile "D:/jackcad2024/subroutine/ba_da.lsp") nil)(/= (findfile "D:/jackcad2024/subroutine/ba_da.fas") nil))(vl-file-delete  "D:/jackcad2024/subroutine/ba_da.lsp"))
(if (and (/= (findfile "D:/jackcad2024/subroutine/bacanamaproyek.LSP") nil)(/= (findfile "D:/jackcad2024/subroutine/bacanamaproyek.fas") nil))(vl-file-delete  "D:/jackcad2024/subroutine/bacanamaproyek.LSP"))
(if (and (/= (findfile "D:/jackcad2024/subroutine/awalprogram.LSP") nil)(/= (findfile "D:/jackcad2024/subroutine/awalprogram.fas") nil))(vl-file-delete  "D:/jackcad2024/subroutine/awalprogram.LSP"))
(if (and (/= (findfile "D:/jackcad2024/Sadap/sub/Denah/Pompa.LSP") nil)(/= (findfile "D:/jackcad2024/Sadap/sub/Denah/Pompa.fas") nil))(vl-file-delete  "D:/jackcad2024/Sadap/sub/Denah/Pompa.LSP"))
(if (and (/= (findfile "D:/jackcad2024/Sadap/sub/Denah/Gorong.LSP") nil)(/= (findfile "D:/jackcad2024/Sadap/sub/Denah/Gorong.fas") nil))(vl-file-delete  "D:/jackcad2024/Sadap/sub/Denah/Gorong.LSP"))
(if (and (/= (findfile "D:/jackcad2024/Sadap/sub/Denah/Dnsal.LSP") nil)(/= (findfile "D:/jackcad2024/Sadap/sub/Denah/Dnsal.fas") nil))(vl-file-delete  "D:/jackcad2024/Sadap/sub/Denah/Dnsal.LSP"))
(if (and (/= (findfile "D:/jackcad2024/Sadap/sub/Denah/Ambang.LSP") nil)(/= (findfile "D:/jackcad2024/Sadap/sub/Denah/Ambang.fas") nil))(vl-file-delete  "D:/jackcad2024/Sadap/sub/Denah/Ambang.LSP"))
(if (and (/= (findfile "D:/jackcad2024/Sadap/sub/simbolair.LSP") nil)(/= (findfile "D:/jackcad2024/Sadap/sub/simbolair.fas") nil))(vl-file-delete  "D:/jackcad2024/Sadap/sub/simbolair.LSP"))
(if (and (/= (findfile "D:/jackcad2024/Sadap/sub/longsambungan.LSP") nil)(/= (findfile "D:/jackcad2024/Sadap/sub/longsambungan.fas") nil))(vl-file-delete  "D:/jackcad2024/Sadap/sub/longsambungan.LSP"))
(if (and (/= (findfile "D:/jackcad2024/Sadap/sub/longsaluran.LSP") nil)(/= (findfile "D:/jackcad2024/Sadap/sub/longsaluran.fas") nil))(vl-file-delete  "D:/jackcad2024/Sadap/sub/longsaluran.LSP"))
(if (and (/= (findfile "D:/jackcad2024/Sadap/sub/longpompa.LSP") nil)(/= (findfile "D:/jackcad2024/Sadap/sub/longpompa.fas") nil))(vl-file-delete  "D:/jackcad2024/Sadap/sub/longpompa.LSP"))
(if (and (/= (findfile "D:/jackcad2024/Sadap/sub/longbelok.LSP") nil)(/= (findfile "D:/jackcad2024/Sadap/sub/longbelok.fas") nil))(vl-file-delete  "D:/jackcad2024/Sadap/sub/longbelok.LSP"))
(if (and (/= (findfile "D:/jackcad2024/Sadap/sub/inmir.LSP") nil)(/= (findfile "D:/jackcad2024/Sadap/sub/inmir.fas") nil))(vl-file-delete  "D:/jackcad2024/Sadap/sub/inmir.LSP"))
(if (and (/= (findfile "D:/jackcad2024/Sadap/sub/crospompa.LSP") nil)(/= (findfile "D:/jackcad2024/Sadap/sub/crospompa.fas") nil))(vl-file-delete  "D:/jackcad2024/Sadap/sub/crospompa.LSP"))
(if (and (/= (findfile "D:/jackcad2024/Sadap/Ukur.lsp") nil)(/= (findfile "D:/jackcad2024/Sadap/Ukur.fas") nil))(vl-file-delete  "D:/jackcad2024/Sadap/Ukur.lsp"))
(if (and (/= (findfile "D:/jackcad2024/Sadap/Terjun.lsp") nil)(/= (findfile "D:/jackcad2024/Sadap/Terjun.fas") nil))(vl-file-delete  "D:/jackcad2024/Sadap/Terjun.lsp"))
(if (and (/= (findfile "D:/jackcad2024/Sadap/Sadap.LSP") nil)(/= (findfile "D:/jackcad2024/Sadap/Sadap.fas") nil))(vl-file-delete  "D:/jackcad2024/Sadap/Sadap.LSP"))
(if (and (/= (findfile "D:/jackcad2024/Sadap/BACA-DAT.LSP") nil)(/= (findfile "D:/jackcad2024/Sadap/BACA-DAT.fas") nil))(vl-file-delete  "D:/jackcad2024/Sadap/BACA-DAT.LSP"))
(if (and (/= (findfile "D:/jackcad2024/Lsp-lain/RM.LSP") nil)(/= (findfile "D:/jackcad2024/Lsp-lain/RM.fas") nil))(vl-file-delete  "D:/jackcad2024/Lsp-lain/RM.LSP"))
(if (and (/= (findfile "D:/jackcad2024/Long/Trase2.lsp") nil)(/= (findfile "D:/jackcad2024/Long/Trase2.fas") nil))(vl-file-delete  "D:/jackcad2024/Long/Trase2.lsp"))
(if (and (/= (findfile "D:/jackcad2024/Long/Trase.lsp") nil)(/= (findfile "D:/jackcad2024/Long/Trase.fas") nil))(vl-file-delete  "D:/jackcad2024/Long/Trase.lsp"))
(if (and (/= (findfile "D:/jackcad2024/Long/O-long.lsp") nil)(/= (findfile "D:/jackcad2024/Long/O-long.fas") nil))(vl-file-delete  "D:/jackcad2024/Long/O-long.lsp"))
(if (and (/= (findfile "D:/jackcad2024/Long/Ld-set.lsp") nil)(/= (findfile "D:/jackcad2024/Long/Ld-set.fas") nil))(vl-file-delete  "D:/jackcad2024/Long/Ld-set.lsp"))
(if (and (/= (findfile "D:/jackcad2024/Long/ins-bgn.LSP") nil)(/= (findfile "D:/jackcad2024/Long/ins-bgn.fas") nil))(vl-file-delete  "D:/jackcad2024/Long/ins-bgn.LSP"))
(if (and (/= (findfile "D:/jackcad2024/Long/grs-renc.LSP") nil)(/= (findfile "D:/jackcad2024/Long/grs-renc.fas") nil))(vl-file-delete  "D:/jackcad2024/Long/grs-renc.LSP"))
(if (and (/= (findfile "D:/jackcad2024/Long/GRS-RENC-step.LSP") nil)(/= (findfile "D:/jackcad2024/Long/GRS-RENC-step.fas") nil))(vl-file-delete  "D:/jackcad2024/Long/GRS-RENC-step.LSP"))
(if (and (/= (findfile "D:/jackcad2024/CROSS/tnh-as.LSP") nil)(/= (findfile "D:/jackcad2024/CROSS/tnh-as.fas") nil))(vl-file-delete  "D:/jackcad2024/CROSS/tnh-as.LSP"))
;;(if (and (/= (findfile "D:/jackcad2024/CROSS/Skatul.lsp") nil)(/= (findfile "D:/jackcad2024/CROSS/Skatul.fas") nil))(vl-file-delete  "D:/jackcad2024/CROSS/Skatul.lsp"))
(if (and (/= (findfile "D:/jackcad2024/CROSS/sal-renc.LSP") nil)(/= (findfile "D:/jackcad2024/CROSS/sal-renc.fas") nil))(vl-file-delete  "D:/jackcad2024/CROSS/sal-renc.LSP"))
(if (and (/= (findfile "D:/jackcad2024/CROSS/SAL-RENC-tn.LSP") nil)(/= (findfile "D:/jackcad2024/CROSS/SAL-RENC-tn.fas") nil))(vl-file-delete  "D:/jackcad2024/CROSS/SAL-RENC-tn.LSP"))
(if (and (/= (findfile "D:/jackcad2024/CROSS/SAL-RENC-step.LSP") nil)(/= (findfile "D:/jackcad2024/CROSS/SAL-RENC-step.fas") nil))(vl-file-delete  "D:/jackcad2024/CROSS/SAL-RENC-step.LSP"))
(if (and (/= (findfile "D:/jackcad2024/CROSS/O-cros.lsp") nil)(/= (findfile "D:/jackcad2024/CROSS/O-cros.fas") nil))(vl-file-delete  "D:/jackcad2024/CROSS/O-cros.lsp"))
(if (and (/= (findfile "D:/jackcad2024/CROSS/NC.LSP") nil)(/= (findfile "D:/jackcad2024/CROSS/NC.fas") nil))(vl-file-delete  "D:/jackcad2024/CROSS/NC.LSP"))
(if (and (/= (findfile "D:/jackcad2024/CROSS/bat-bebas.LSP") nil)(/= (findfile "D:/jackcad2024/CROSS/bat-bebas.fas") nil))(vl-file-delete  "D:/jackcad2024/CROSS/bat-bebas.LSP"))
(if (and (/= (findfile "D:/jackcad2024/Boks/sub/Sal6c.LSP") nil)(/= (findfile "D:/jackcad2024/Boks/sub/Sal6c.fas") nil))(vl-file-delete  "D:/jackcad2024/Boks/sub/Sal6c.LSP"))
(if (and (/= (findfile "D:/jackcad2024/Boks/sub/Sal6b.LSP") nil)(/= (findfile "D:/jackcad2024/Boks/sub/Sal6b.fas") nil))(vl-file-delete  "D:/jackcad2024/Boks/sub/Sal6b.LSP"))
(if (and (/= (findfile "D:/jackcad2024/Boks/sub/Sal6.LSP") nil)(/= (findfile "D:/jackcad2024/Boks/sub/Sal6.fas") nil))(vl-file-delete  "D:/jackcad2024/Boks/sub/Sal6.LSP"))
(if (and (/= (findfile "D:/jackcad2024/Boks/sub/Sal4i.LSP") nil)(/= (findfile "D:/jackcad2024/Boks/sub/Sal4i.fas") nil))(vl-file-delete  "D:/jackcad2024/Boks/sub/Sal4i.LSP"))
(if (and (/= (findfile "D:/jackcad2024/Boks/sub/Sal4h.LSP") nil)(/= (findfile "D:/jackcad2024/Boks/sub/Sal4h.fas") nil))(vl-file-delete  "D:/jackcad2024/Boks/sub/Sal4h.LSP"))
(if (and (/= (findfile "D:/jackcad2024/Boks/sub/Sal4g.LSP") nil)(/= (findfile "D:/jackcad2024/Boks/sub/Sal4g.fas") nil))(vl-file-delete  "D:/jackcad2024/Boks/sub/Sal4g.LSP"))
(if (and (/= (findfile "D:/jackcad2024/Boks/sub/Sal4f.LSP") nil)(/= (findfile "D:/jackcad2024/Boks/sub/Sal4f.fas") nil))(vl-file-delete  "D:/jackcad2024/Boks/sub/Sal4f.LSP"))
(if (and (/= (findfile "D:/jackcad2024/Boks/sub/Sal4e.LSP") nil)(/= (findfile "D:/jackcad2024/Boks/sub/Sal4e.fas") nil))(vl-file-delete  "D:/jackcad2024/Boks/sub/Sal4e.LSP"))
(if (and (/= (findfile "D:/jackcad2024/Boks/sub/Sal4d.LSP") nil)(/= (findfile "D:/jackcad2024/Boks/sub/Sal4d.fas") nil))(vl-file-delete  "D:/jackcad2024/Boks/sub/Sal4d.LSP"))
(if (and (/= (findfile "D:/jackcad2024/Boks/sub/Sal4c.LSP") nil)(/= (findfile "D:/jackcad2024/Boks/sub/Sal4c.fas") nil))(vl-file-delete  "D:/jackcad2024/Boks/sub/Sal4c.LSP"))
(if (and (/= (findfile "D:/jackcad2024/Boks/sub/Sal4b.LSP") nil)(/= (findfile "D:/jackcad2024/Boks/sub/Sal4b.fas") nil))(vl-file-delete  "D:/jackcad2024/Boks/sub/Sal4b.LSP"))
(if (and (/= (findfile "D:/jackcad2024/Boks/sub/Sal4.LSP") nil)(/= (findfile "D:/jackcad2024/Boks/sub/Sal4.fas") nil))(vl-file-delete  "D:/jackcad2024/Boks/sub/Sal4.LSP"))
(if (and (/= (findfile "D:/jackcad2024/Boks/sub/Sal2c.LSP") nil)(/= (findfile "D:/jackcad2024/Boks/sub/Sal2c.fas") nil))(vl-file-delete  "D:/jackcad2024/Boks/sub/Sal2c.LSP"))
(if (and (/= (findfile "D:/jackcad2024/Boks/sub/Sal2b.LSP") nil)(/= (findfile "D:/jackcad2024/Boks/sub/Sal2b.fas") nil))(vl-file-delete  "D:/jackcad2024/Boks/sub/Sal2b.LSP"))
(if (and (/= (findfile "D:/jackcad2024/Boks/sub/Sal2.LSP") nil)(/= (findfile "D:/jackcad2024/Boks/sub/Sal2.fas") nil))(vl-file-delete  "D:/jackcad2024/Boks/sub/Sal2.LSP"))
(if (and (/= (findfile "D:/jackcad2024/Boks/sub/Sal1.LSP") nil)(/= (findfile "D:/jackcad2024/Boks/sub/Sal1.fas") nil))(vl-file-delete  "D:/jackcad2024/Boks/sub/Sal1.LSP"))
(if (and (/= (findfile "D:/jackcad2024/Boks/sub/PML6bc.LSP") nil)(/= (findfile "D:/jackcad2024/Boks/sub/PML6bc.fas") nil))(vl-file-delete  "D:/jackcad2024/Boks/sub/PML6bc.LSP"))
(if (and (/= (findfile "D:/jackcad2024/Boks/sub/PML6.LSP") nil)(/= (findfile "D:/jackcad2024/Boks/sub/PML6.fas") nil))(vl-file-delete  "D:/jackcad2024/Boks/sub/PML6.LSP"))
(if (and (/= (findfile "D:/jackcad2024/Boks/sub/PML4fghi.LSP") nil)(/= (findfile "D:/jackcad2024/Boks/sub/PML4fghi.fas") nil))(vl-file-delete  "D:/jackcad2024/Boks/sub/PML4fghi.LSP"))
(if (and (/= (findfile "D:/jackcad2024/Boks/sub/PML4de.LSP") nil)(/= (findfile "D:/jackcad2024/Boks/sub/PML4de.fas") nil))(vl-file-delete  "D:/jackcad2024/Boks/sub/PML4de.LSP"))
(if (and (/= (findfile "D:/jackcad2024/Boks/sub/PML4BC.LSP") nil)(/= (findfile "D:/jackcad2024/Boks/sub/PML4BC.fas") nil))(vl-file-delete  "D:/jackcad2024/Boks/sub/PML4BC.LSP"))
(if (and (/= (findfile "D:/jackcad2024/Boks/sub/PML4.LSP") nil)(/= (findfile "D:/jackcad2024/Boks/sub/PML4.fas") nil))(vl-file-delete  "D:/jackcad2024/Boks/sub/PML4.LSP"))
(if (and (/= (findfile "D:/jackcad2024/Boks/sub/PML2bc.LSP") nil)(/= (findfile "D:/jackcad2024/Boks/sub/PML2bc.fas") nil))(vl-file-delete  "D:/jackcad2024/Boks/sub/PML2bc.LSP"))
(if (and (/= (findfile "D:/jackcad2024/Boks/sub/PML2.LSP") nil)(/= (findfile "D:/jackcad2024/Boks/sub/PML2.fas") nil))(vl-file-delete  "D:/jackcad2024/Boks/sub/PML2.LSP"))
(if (and (/= (findfile "D:/jackcad2024/Boks/sub/PMl1.lsp") nil)(/= (findfile "D:/jackcad2024/Boks/sub/PMl1.fas") nil))(vl-file-delete  "D:/jackcad2024/Boks/sub/PMl1.lsp"))
(if (and (/= (findfile "D:/jackcad2024/Boks/sub/pl3.LSP") nil)(/= (findfile "D:/jackcad2024/Boks/sub/pl3.fas") nil))(vl-file-delete  "D:/jackcad2024/Boks/sub/pl3.LSP"))
(if (and (/= (findfile "D:/jackcad2024/Boks/sub/pl2.LSP") nil)(/= (findfile "D:/jackcad2024/Boks/sub/pl2.fas") nil))(vl-file-delete  "D:/jackcad2024/Boks/sub/pl2.LSP"))
(if (and (/= (findfile "D:/jackcad2024/Boks/sub/pl1.LSP") nil)(/= (findfile "D:/jackcad2024/Boks/sub/pl1.fas") nil))(vl-file-delete  "D:/jackcad2024/Boks/sub/pl1.LSP"))
(if (and (/= (findfile "D:/jackcad2024/Boks/sub/Longc2.LSP") nil)(/= (findfile "D:/jackcad2024/Boks/sub/Longc2.fas") nil))(vl-file-delete  "D:/jackcad2024/Boks/sub/Longc2.LSP"))
(if (and (/= (findfile "D:/jackcad2024/Boks/sub/Longc1.LSP") nil)(/= (findfile "D:/jackcad2024/Boks/sub/Longc1.fas") nil))(vl-file-delete  "D:/jackcad2024/Boks/sub/Longc1.LSP"))
(if (and (/= (findfile "D:/jackcad2024/Boks/sub/Longb5.LSP") nil)(/= (findfile "D:/jackcad2024/Boks/sub/Longb5.fas") nil))(vl-file-delete  "D:/jackcad2024/Boks/sub/Longb5.LSP"))
(if (and (/= (findfile "D:/jackcad2024/Boks/sub/Longb4.LSP") nil)(/= (findfile "D:/jackcad2024/Boks/sub/Longb4.fas") nil))(vl-file-delete  "D:/jackcad2024/Boks/sub/Longb4.LSP"))
(if (and (/= (findfile "D:/jackcad2024/Boks/sub/Longb3.LSP") nil)(/= (findfile "D:/jackcad2024/Boks/sub/Longb3.fas") nil))(vl-file-delete  "D:/jackcad2024/Boks/sub/Longb3.LSP"))
(if (and (/= (findfile "D:/jackcad2024/Boks/sub/Longb2.LSP") nil)(/= (findfile "D:/jackcad2024/Boks/sub/Longb2.fas") nil))(vl-file-delete  "D:/jackcad2024/Boks/sub/Longb2.LSP"))
(if (and (/= (findfile "D:/jackcad2024/Boks/sub/Longb1.LSP") nil)(/= (findfile "D:/jackcad2024/Boks/sub/Longb1.fas") nil))(vl-file-delete  "D:/jackcad2024/Boks/sub/Longb1.LSP"))
(if (and (/= (findfile "D:/jackcad2024/Boks/sub/Longa3.LSP") nil)(/= (findfile "D:/jackcad2024/Boks/sub/Longa3.fas") nil))(vl-file-delete  "D:/jackcad2024/Boks/sub/Longa3.LSP"))
(if (and (/= (findfile "D:/jackcad2024/Boks/sub/Longa2.LSP") nil)(/= (findfile "D:/jackcad2024/Boks/sub/Longa2.fas") nil))(vl-file-delete  "D:/jackcad2024/Boks/sub/Longa2.LSP"))
(if (and (/= (findfile "D:/jackcad2024/Boks/sub/Long1.LSP") nil)(/= (findfile "D:/jackcad2024/Boks/sub/Long1.fas") nil))(vl-file-delete  "D:/jackcad2024/Boks/sub/Long1.LSP"))
(if (and (/= (findfile "D:/jackcad2024/bangunan/o-bangunan.LSP") nil)(/= (findfile "D:/jackcad2024/bangunan/o-bangunan.fas") nil))(vl-file-delete  "D:/jackcad2024/bangunan/o-bangunan.LSP"))
(if (and (/= (findfile "D:/jackcad2024/TU-SET.LSP") nil)(/= (findfile "D:/jackcad2024/TU-SET.fas") nil))(vl-file-delete  "D:/jackcad2024/TU-SET.LSP"))
(if (and (/= (findfile "D:/jackcad2024/RE-SET.LSP") nil)(/= (findfile "D:/jackcad2024/RE-SET.fas") nil))(vl-file-delete  "D:/jackcad2024/RE-SET.LSP"))
(if (and (/= (findfile "D:/jackcad2024/Pter.LSP") nil)(/= (findfile "D:/jackcad2024/Pter.fas") nil))(vl-file-delete  "D:/jackcad2024/Pter.LSP"))
(if (and (/= (findfile "D:/jackcad2024/Pkwar.LSP") nil)(/= (findfile "D:/jackcad2024/Pkwar.fas") nil))(vl-file-delete  "D:/jackcad2024/Pkwar.LSP"))
(if (and (/= (findfile "D:/jackcad2024/op-file.LSP") nil)(/= (findfile "D:/jackcad2024/op-file.fas") nil))(vl-file-delete  "D:/jackcad2024/op-file.LSP"))
(if (and (/= (findfile "D:/jackcad2024/Boks/sub/KOTAK.LSP") nil)(/= (findfile "D:/jackcad2024/Boks/sub/KOTAK.fas") nil))(vl-file-delete  "D:/jackcad2024/Boks/sub/KOTAK.LSP"))
(if (and (/= (findfile "D:/jackcad2024/subroutine/arsirmiring.LSP") nil)(/= (findfile "D:/jackcad2024/subroutine/arsirmiring.fas") nil))(vl-file-delete  "D:/jackcad2024/subroutine/arsirmiring.LSP"))
(if (and (/= (findfile "D:/jackcad2024/subroutine/arsirtanah.LSP") nil)(/= (findfile "D:/jackcad2024/subroutine/arsirtanah.fas") nil))(vl-file-delete  "D:/jackcad2024/subroutine/arsirtanah.LSP"))
(if (and (/= (findfile "D:/jackcad2024/subroutine/hatchmiring.LSP") nil)(/= (findfile "D:/jackcad2024/subroutine/hatchmiring.fas") nil))(vl-file-delete  "D:/jackcad2024/subroutine/hatchmiring.LSP"))
(if (and (/= (findfile "D:/jackcad2024/CROSS/re-dim.lsp") nil)(/= (findfile "D:/jackcad2024/CROSS/re-dim.fas") nil))(vl-file-delete  "D:/jackcad2024/CROSS/re-dim.lsp"))
(if (and (/= (findfile "D:/jackcad2024/CROSS/pasangan.LSP") nil)(/= (findfile "D:/jackcad2024/CROSS/pasangan.fas") nil))(vl-file-delete  "D:/jackcad2024/CROSS/pasangan.LSP"))
(if (and (/= (findfile "D:/jackcad2024/CROSS/car-lok.LSP") nil)(/= (findfile "D:/jackcad2024/CROSS/car-lok.fas") nil))(vl-file-delete  "D:/jackcad2024/CROSS/car-lok.LSP"))
(if (and (/= (findfile "D:/jackcad2024/Sadap/sub/crossal.LSP") nil)(/= (findfile "D:/jackcad2024/Sadap/sub/crossal.fas") nil))(vl-file-delete  "D:/jackcad2024/Sadap/sub/crossal.LSP"))
(if (and (/= (findfile "D:/jackcad2024/Sadap/sub/KO-TEK2.LSP") nil)(/= (findfile "D:/jackcad2024/Sadap/sub/KO-TEK2.fas") nil))(vl-file-delete  "D:/jackcad2024/Sadap/sub/KO-TEK2.LSP"))
(if (and (/= (findfile "D:/jackcad2024/Sadap/sub/BOQ/Boqsaluran.LSP") nil)(/= (findfile "D:/jackcad2024/Sadap/sub/BOQ/Boqsaluran.fas") nil))(vl-file-delete  "D:/jackcad2024/Sadap/sub/BOQ/Boqsaluran.LSP"))
(if (and (/= (findfile "D:/jackcad2024/Sadap/sub/dimsal.LSP") nil)(/= (findfile "D:/jackcad2024/Sadap/sub/dimsal.fas") nil))(vl-file-delete  "D:/jackcad2024/Sadap/sub/dimsal.LSP"))
(if (and (/= (findfile "D:/jackcad2024/subroutine/serialnumber.LSP") nil)(/= (findfile "D:/jackcad2024/subroutine/serialnumber.fas") nil))(vl-file-delete  "D:/jackcad2024/subroutine/serialnumber.LSP"))
(if (and (/= (findfile "D:/jackcad2024/subroutine/snc.LSP") nil)(/= (findfile "D:/jackcad2024/subroutine/snc.fas") nil))(vl-file-delete  "D:/jackcad2024/subroutine/snc.LSP"))
(if (and (/= (findfile "D:/jackcad2024/subroutine/copyfolder.LSP") nil)(/= (findfile "D:/jackcad2024/subroutine/copyfolder.fas") nil))(vl-file-delete  "D:/jackcad2024/subroutine/copyfolder.LSP"))
(if (and (/= (findfile "D:/jackcad2024/Sadap/RM2.LSP") nil)(/= (findfile "D:/jackcad2024/Sadap/RM2.fas") nil))(vl-file-delete  "D:/jackcad2024/Sadap/RM2.LSP"))
(if (and (/= (findfile "D:/jackcad2024/Sadap/sub/crospintu.LSP") nil)(/= (findfile "D:/jackcad2024/Sadap/sub/crospintu.fas") nil))(vl-file-delete  "D:/jackcad2024/Sadap/sub/crospintu.LSP"))
(if (and (/= (findfile "D:/jackcad2024/Sadap/sub/longpintu.LSP") nil)(/= (findfile "D:/jackcad2024/Sadap/sub/longpintu.fas") nil))(vl-file-delete  "D:/jackcad2024/Sadap/sub/longpintu.LSP"))
(if (and (/= (findfile "D:/jackcad2024/Sadap/sub/longgorong.LSP") nil)(/= (findfile "D:/jackcad2024/Sadap/sub/longgorong.fas") nil))(vl-file-delete  "D:/jackcad2024/Sadap/sub/longgorong.LSP"))
(if (and (/= (findfile "D:/jackcad2024/Sadap/sub/crosgorong.LSP") nil)(/= (findfile "D:/jackcad2024/Sadap/sub/crosgorong.fas") nil))(vl-file-delete  "D:/jackcad2024/Sadap/sub/crosgorong.LSP"))
(if (and (/= (findfile "D:/jackcad2024/Sadap/sub/longambang.LSP") nil)(/= (findfile "D:/jackcad2024/Sadap/sub/longambang.fas") nil))(vl-file-delete  "D:/jackcad2024/Sadap/sub/longambang.LSP"))
(if (and (/= (findfile "D:/jackcad2024/Sadap/sub/awalkotak.LSP") nil)(/= (findfile "D:/jackcad2024/Sadap/sub/awalkotak.fas") nil))(vl-file-delete  "D:/jackcad2024/Sadap/sub/awalkotak.LSP"))
(if (and (/= (findfile "D:/jackcad2024/Sadap/sub/crosambang.LSP") nil)(/= (findfile "D:/jackcad2024/Sadap/sub/crosambang.fas") nil))(vl-file-delete  "D:/jackcad2024/Sadap/sub/crosambang.LSP"))
(if (and (/= (findfile "D:/jackcad2024/subroutine/TeksDimensi.LSP") nil)(/= (findfile "D:/jackcad2024/subroutine/TeksDimensi.fas") nil))(vl-file-delete  "D:/jackcad2024/subroutine/TeksDimensi.LSP"))
(if (and (/= (findfile "D:/jackcad2024/subroutine/settinghuruf.LSP") nil)(/= (findfile "D:/jackcad2024/subroutine/settinghuruf.fas") nil))(vl-file-delete  "D:/jackcad2024/subroutine/settinghuruf.LSP"))
(if (and (/= (findfile "D:/jackcad2024/subroutine/teks-elevasi.LSP") nil)(/= (findfile "D:/jackcad2024/subroutine/teks-elevasi.fas") nil))(vl-file-delete  "D:/jackcad2024/subroutine/teks-elevasi.LSP"))
(if (and (/= (findfile "D:/jackcad2024/Sadap/sub/T-E.LSP") nil)(/= (findfile "D:/jackcad2024/Sadap/sub/T-E.fas") nil))(vl-file-delete  "D:/jackcad2024/Sadap/sub/T-E.LSP"))
(if (and (/= (findfile "D:/jackcad2024/Sadap/sub/sdbulat.LSP") nil)(/= (findfile "D:/jackcad2024/Sadap/sub/sdbulat.fas") nil))(vl-file-delete  "D:/jackcad2024/Sadap/sub/sdbulat.LSP"))
(if (and (/= (findfile "D:/jackcad2024/Sadap/sub/belno.LSP") nil)(/= (findfile "D:/jackcad2024/Sadap/sub/belno.fas") nil))(vl-file-delete  "D:/jackcad2024/Sadap/sub/belno.LSP"))
(if (and (/= (findfile "D:/jackcad2024/Sadap/sub/MR1a.LSP") nil)(/= (findfile "D:/jackcad2024/Sadap/sub/MR1a.fas") nil))(vl-file-delete  "D:/jackcad2024/Sadap/sub/MR1a.LSP"))
(if (and (/= (findfile "D:/jackcad2024/Sadap/sub/awalsdakhir.LSP") nil)(/= (findfile "D:/jackcad2024/Sadap/sub/awalsdakhir.fas") nil))(vl-file-delete  "D:/jackcad2024/Sadap/sub/awalsdakhir.LSP"))
(if (and (/= (findfile "D:/jackcad2024/Sadap/sub/settingsaluranawal.LSP") nil)(/= (findfile "D:/jackcad2024/Sadap/sub/settingsaluranawal.fas") nil))(vl-file-delete  "D:/jackcad2024/Sadap/sub/settingsaluranawal.LSP"))
(if (and (/= (findfile "D:/jackcad2024/Sadap/sub/settingsaluranakhir.LSP") nil)(/= (findfile "D:/jackcad2024/Sadap/sub/settingsaluranakhir.fas") nil))(vl-file-delete  "D:/jackcad2024/Sadap/sub/settingsaluranakhir.LSP"))
(if (and (/= (findfile "D:/jackcad2024/Sadap/sub/dimlama.LSP") nil)(/= (findfile "D:/jackcad2024/Sadap/sub/dimlama.fas") nil))(vl-file-delete  "D:/jackcad2024/Sadap/sub/dimlama.LSP"))
(if (and (/= (findfile "D:/jackcad2024/Long/tul-leng.LSP") nil)(/= (findfile "D:/jackcad2024/Long/tul-leng.fas") nil))(vl-file-delete  "D:/jackcad2024/Long/tul-leng.LSP"))
(if (and (/= (findfile "D:/jackcad2024/Long/da-long.LSP") nil)(/= (findfile "D:/jackcad2024/Long/da-long.fas") nil))(vl-file-delete  "D:/jackcad2024/Long/da-long.LSP"))
(if (and (/= (findfile "D:/jackcad2024/Long/FKURVA.LSP") nil)(/= (findfile "D:/jackcad2024/Long/FKURVA.fas") nil))(vl-file-delete  "D:/jackcad2024/Long/FKURVA.LSP"))
(if (and (/= (findfile "D:/jackcad2024/CROSS/te-ja.LSP") nil)(/= (findfile "D:/jackcad2024/CROSS/te-ja.fas") nil))(vl-file-delete  "D:/jackcad2024/CROSS/te-ja.LSP"))
(if (and (/= (findfile "D:/jackcad2024/CROSS/aturc.LSP") nil)(/= (findfile "D:/jackcad2024/CROSS/aturc.fas") nil))(vl-file-delete  "D:/jackcad2024/CROSS/aturc.LSP"))
(if (and (/= (findfile "D:/jackcad2024/CROSS/tul-dim.LSP") nil)(/= (findfile "D:/jackcad2024/CROSS/tul-dim.fas") nil))(vl-file-delete  "D:/jackcad2024/CROSS/tul-dim.LSP"))
(if (and (/= (findfile "D:/jackcad2024/CROSS/TUL-DIM-step.LSP") nil)(/= (findfile "D:/jackcad2024/CROSS/TUL-DIM-step.fas") nil))(vl-file-delete  "D:/jackcad2024/CROSS/TUL-DIM-step.LSP"))
(if (and (/= (findfile "D:/jackcad2024/CROSS/tul-datpat.LSP") nil)(/= (findfile "D:/jackcad2024/CROSS/tul-datpat.fas") nil))(vl-file-delete  "D:/jackcad2024/CROSS/tul-datpat.LSP"))
(if (and (/= (findfile "D:/jackcad2024/CROSS/T-E.LSP") nil)(/= (findfile "D:/jackcad2024/CROSS/T-E.fas") nil))(vl-file-delete  "D:/jackcad2024/CROSS/T-E.LSP"))
(if (and (/= (findfile "D:/jackcad2024/CROSS/jalan.LSP") nil)(/= (findfile "D:/jackcad2024/CROSS/jalan.fas") nil))(vl-file-delete  "D:/jackcad2024/CROSS/jalan.LSP"))
(if (and (/= (findfile "D:/jackcad2024/CROSS/gam.LSP") nil)(/= (findfile "D:/jackcad2024/CROSS/gam.fas") nil))(vl-file-delete  "D:/jackcad2024/CROSS/gam.LSP"))
(if (and (/= (findfile "D:/jackcad2024/Long/TUL-DAT.LSP") nil)(/= (findfile "D:/jackcad2024/Long/TUL-DAT.fas") nil))(vl-file-delete  "D:/jackcad2024/Long/TUL-DAT.LSP"))
(if (and (/= (findfile "D:/jackcad2024/Long/TUL-DAT-step.LSP") nil)(/= (findfile "D:/jackcad2024/Long/TUL-DAT-step.fas") nil))(vl-file-delete  "D:/jackcad2024/Long/TUL-DAT-step.LSP"))
(if (and (/= (findfile "D:/jackcad2024/Long/SKALA-V.LSP") nil)(/= (findfile "D:/jackcad2024/Long/SKALA-V.fas") nil))(vl-file-delete  "D:/jackcad2024/Long/SKALA-V.LSP"))
(if (and (/= (findfile "D:/jackcad2024/Long/hektom.LSP") nil)(/= (findfile "D:/jackcad2024/Long/hektom.fas") nil))(vl-file-delete  "D:/jackcad2024/Long/hektom.LSP"))
(if (and (/= (findfile "D:/jackcad2024/Long/TUL-DIM-step.LSP") nil)(/= (findfile "D:/jackcad2024/Long/TUL-DIM-step.fas") nil))(vl-file-delete  "D:/jackcad2024/Long/TUL-DIM-step.LSP"))
(if (and (/= (findfile "D:/jackcad2024/Long/D-C2.LSP") nil)(/= (findfile "D:/jackcad2024/Long/D-C2.fas") nil))(vl-file-delete  "D:/jackcad2024/Long/D-C2.LSP"))
(if (and (/= (findfile "D:/jackcad2024/Long/D-C1.LSP") nil)(/= (findfile "D:/jackcad2024/Long/D-C1.fas") nil))(vl-file-delete  "D:/jackcad2024/Long/D-C1.LSP"))
(if (and (/= (findfile "D:/jackcad2024/Long/DIMDRAIN.LSP") nil)(/= (findfile "D:/jackcad2024/Long/DIMDRAIN.fas") nil))(vl-file-delete  "D:/jackcad2024/Long/DIMDRAIN.LSP"))
(if (and (/= (findfile "D:/jackcad2024/Long/DIMCANAL.LSP") nil)(/= (findfile "D:/jackcad2024/Long/DIMCANAL.fas") nil))(vl-file-delete  "D:/jackcad2024/Long/DIMCANAL.LSP"))
(if (and (/= (findfile "D:/jackcad2024/bangunan/aturBangunan.LSP") nil)(/= (findfile "D:/jackcad2024/bangunan/aturBangunan.fas") nil))(vl-file-delete  "D:/jackcad2024/bangunan/aturBangunan.LSP"))
(if (and (/= (findfile "D:/jackcad2024/Topo/Bacadatasituasi.lsp") nil)(/= (findfile "D:/jackcad2024/Topo/Bacadatasituasi.fas") nil))(vl-file-delete  "D:/jackcad2024/Topo/Bacadatasituasi.lsp"))
(if (and (/= (findfile "D:/jackcad2024/Topo/aturS.LSP") nil)(/= (findfile "D:/jackcad2024/Topo/aturS.fas") nil))(vl-file-delete  "D:/jackcad2024/Topo/aturS.LSP"))
(if (and (/= (findfile "D:/jackcad2024/subroutine/setqp.LSP") nil)(/= (findfile "D:/jackcad2024/subroutine/setqp.fas") nil))(vl-file-delete  "D:/jackcad2024/subroutine/setqp.LSP"))
(if (and (/= (findfile "D:/jackcad2024/subroutine/daftarautolip.lsp") nil)(/= (findfile "D:/jackcad2024/subroutine/daftarautolip.fas") nil))(vl-file-delete  "D:/jackcad2024/subroutine/daftarautolip.lsp"))
(if (and (/= (findfile "D:/jackcad2024/CROSS/warna.LSP") nil)(/= (findfile "D:/jackcad2024/CROSS/warna.fas") nil))(vl-file-delete  "D:/jackcad2024/CROSS/warna.LSP"))
(if (and (/= (findfile "D:/jackcad2024/subroutine/bangunan/tip-PAS.LSP") nil)(/= (findfile "D:/jackcad2024/subroutine/bangunan/tip-PAS.fas") nil))(vl-file-delete  "D:/jackcad2024/subroutine/bangunan/tip-PAS.LSP"))
(if (and (/= (findfile "D:/jackcad2024/arsir4.LSP") nil)(/= (findfile "D:/jackcad2024/arsir4.fas") nil))(vl-file-delete  "D:/jackcad2024/arsir4.LSP"))
(if (and (/= (findfile "D:/jackcad2024/Terjunan/sub/KO-TEK.LSP") nil)(/= (findfile "D:/jackcad2024/Terjunan/sub/KO-TEK.fas") nil))(vl-file-delete  "D:/jackcad2024/Terjunan/sub/KO-TEK.LSP"))
(if (and (/= (findfile "D:/jackcad2024/inisial.LSP") nil)(/= (findfile "D:/jackcad2024/inisial.fas") nil))(vl-file-delete  "D:/jackcad2024/inisial.LSP"))
(if (and (/= (findfile "D:/jackcad2024/subroutine/inisial.LSP") nil)(/= (findfile "D:/jackcad2024/subroutine/inisial.fas") nil))(vl-file-delete  "D:/jackcad2024/subroutine/inisial.LSP"))
;;;(if (and (/= (findfile "D:/jackcad2024/subroutine/rubahukuranhuruf.LSP") nil)(/= (findfile "D:/jackcad2024/subroutine/rubahukuranhuruf.fas") nil))(vl-file-delete  "D:/jackcad2024/subroutine/rubahukuranhuruf.LSP"))
(if (and (/= (findfile "D:/jackcad2024/subroutine/rubahelevasi.LSP") nil)(/= (findfile "D:/jackcad2024/subroutine/rubahelevasi.fas") nil))(vl-file-delete  "D:/jackcad2024/subroutine/rubahelevasi.LSP"))
(if (and (/= (findfile "D:/jackcad2024/subroutine/putartext.LSP") nil)(/= (findfile "D:/jackcad2024/subroutine/putartext.fas") nil))(vl-file-delete  "D:/jackcad2024/subroutine/putartext.LSP"))
(if (and (/= (findfile "D:/jackcad2024/subroutine/bacadataformtab.lsp") nil)(/= (findfile "D:/jackcad2024/subroutine/bacadataformtab.fas") nil))(vl-file-delete  "D:/jackcad2024/subroutine/bacadataformtab.lsp"))
(if (and (/= (findfile "D:/jackcad2024/subroutine/bacadataexcel.lsp") nil)(/= (findfile "D:/jackcad2024/subroutine/bacadataexcel.fas") nil))(vl-file-delete  "D:/jackcad2024/subroutine/bacadataexcel.lsp"))
(if (and (/= (findfile "D:/jackcad2024/subroutine/azimuth.LSP") nil)(/= (findfile "D:/jackcad2024/subroutine/azimuth.fas") nil))(vl-file-delete  "D:/jackcad2024/subroutine/azimuth.LSP"))
(if (and (/= (findfile "D:/jackcad2024/subroutine/bacalokjudul.LSP") nil)(/= (findfile "D:/jackcad2024/subroutine/bacalokjudul.fas") nil))(vl-file-delete  "D:/jackcad2024/subroutine/bacalokjudul.LSP"))
(if (and (/= (findfile "D:/jackcad2024/subroutine/bangunan/Kotakdimensi.LSP") nil)(/= (findfile "D:/jackcad2024/subroutine/bangunan/Kotakdimensi.fas") nil))(vl-file-delete  "D:/jackcad2024/subroutine/bangunan/Kotakdimensi.LSP"))
(if (and (/= (findfile "D:/jackcad2024/Boks/sub/KO-TEK.LSP") nil)(/= (findfile "D:/jackcad2024/Boks/sub/KO-TEK.fas") nil))(vl-file-delete  "D:/jackcad2024/Boks/sub/KO-TEK.LSP"))
(if (and (/= (findfile "D:/jackcad2024/subroutine/Browsefolder.lsp") nil)(/= (findfile "D:/jackcad2024/subroutine/Browsefolder.fas") nil))(vl-file-delete  "D:/jackcad2024/subroutine/Browsefolder.lsp"))
(if (and (/= (findfile "D:/jackcad2024/CROSS/re-fi.LSP") nil)(/= (findfile "D:/jackcad2024/CROSS/re-fi.fas") nil))(vl-file-delete  "D:/jackcad2024/CROSS/re-fi.LSP"))
(if (and (/= (findfile "D:/jackcad2024/Long/tip-PAS.LSP") nil)(/= (findfile "D:/jackcad2024/Long/tip-PAS.fas") nil))(vl-file-delete  "D:/jackcad2024/Long/tip-PAS.LSP"))
;;(if (and (/= (findfile "D:/jackcad2024/CROSS/Skat_l.lsp") nil)(/= (findfile "D:/jackcad2024/CROSS/Skat_l.fas") nil))(vl-file-delete  "D:/jackcad2024/CROSS/Skat_l.lsp"))
(if (and (/= (findfile "D:/jackcad2024/Sadap/sub/BOQ/boqpompa.LSP") nil)(/= (findfile "D:/jackcad2024/Sadap/sub/BOQ/boqpompa.fas") nil))(vl-file-delete  "D:/jackcad2024/Sadap/sub/BOQ/boqpompa.LSP"))
(if (and (/= (findfile "D:/jackcad2024/Sadap/sub/BOQ/boqambang.LSP") nil)(/= (findfile "D:/jackcad2024/Sadap/sub/BOQ/boqambang.fas") nil))(vl-file-delete  "D:/jackcad2024/Sadap/sub/BOQ/boqambang.LSP"))
(if (and (/= (findfile "D:/jackcad2024/Sadap/sub/BOQ/boqgorong.LSP") nil)(/= (findfile "D:/jackcad2024/Sadap/sub/BOQ/boqgorong.fas") nil))(vl-file-delete  "D:/jackcad2024/Sadap/sub/BOQ/boqgorong.LSP"))
(if (and (/= (findfile "D:/jackcad2024/Sadap/sub/BOQ/boqsambungan.LSP") nil)(/= (findfile "D:/jackcad2024/Sadap/sub/BOQ/boqsambungan.fas") nil))(vl-file-delete  "D:/jackcad2024/Sadap/sub/BOQ/boqsambungan.LSP"))
(if (and (/= (findfile "D:/jackcad2024/Sadap/sub/BOQ/boqpintu.LSP") nil)(/= (findfile "D:/jackcad2024/Sadap/sub/BOQ/boqpintu.fas") nil))(vl-file-delete  "D:/jackcad2024/Sadap/sub/BOQ/boqpintu.LSP"))
(if (and (/= (findfile "D:/jackcad2024/Sadap/sub/BOQ/boqbelokan.LSP") nil)(/= (findfile "D:/jackcad2024/Sadap/sub/BOQ/boqbelokan.fas") nil))(vl-file-delete  "D:/jackcad2024/Sadap/sub/BOQ/boqbelokan.LSP"))
(if (and (/= (findfile "D:/jackcad2024/Sadap/sub/setlay.LSP") nil)(/= (findfile "D:/jackcad2024/Sadap/sub/setlay.fas") nil))(vl-file-delete  "D:/jackcad2024/Sadap/sub/setlay.LSP"))
(if (and (/= (findfile "D:/jackcad2024/Sadap/sub/Denah/Pintu.LSP") nil)(/= (findfile "D:/jackcad2024/Sadap/sub/Denah/Pintu.fas") nil))(vl-file-delete  "D:/jackcad2024/Sadap/sub/Denah/Pintu.LSP"))
(if (and (/= (findfile "D:/jackcad2024/Sadap/sub/koperup.lsp") nil)(/= (findfile "D:/jackcad2024/Sadap/sub/koperup.fas") nil))(vl-file-delete  "D:/jackcad2024/Sadap/sub/koperup.lsp"))
(if (and (/= (findfile "D:/jackcad2024/Sadap/carilokasi.LSP") nil)(/= (findfile "D:/jackcad2024/Sadap/carilokasi.fas") nil))(vl-file-delete  "D:/jackcad2024/Sadap/carilokasi.LSP"))
(if (and (/= (findfile "D:/jackcad2024/Sadap/sub/Denah/Dnbelok.LSP") nil)(/= (findfile "D:/jackcad2024/Sadap/sub/Denah/Dnbelok.fas") nil))(vl-file-delete  "D:/jackcad2024/Sadap/sub/Denah/Dnbelok.LSP"))
(if (and (/= (findfile "D:/jackcad2024/Sadap/sub/Denah/sambungan.LSP") nil)(/= (findfile "D:/jackcad2024/Sadap/sub/Denah/sambungan.fas") nil))(vl-file-delete  "D:/jackcad2024/Sadap/sub/Denah/sambungan.LSP"))
(if (and (/= (findfile "D:/jackcad2024/Sadap/sub/Dnpier.LSP") nil)(/= (findfile "D:/jackcad2024/Sadap/sub/Dnpier.fas") nil))(vl-file-delete  "D:/jackcad2024/Sadap/sub/Dnpier.LSP"))
(if (and (/= (findfile "D:/jackcad2024/Sadap/sub/Dnpusat.LSP") nil)(/= (findfile "D:/jackcad2024/Sadap/sub/Dnpusat.fas") nil))(vl-file-delete  "D:/jackcad2024/Sadap/sub/Dnpusat.LSP"))
(if (and (/= (findfile "D:/jackcad2024/Sadap/sub/DtRd.LSP") nil)(/= (findfile "D:/jackcad2024/Sadap/sub/DtRd.fas") nil))(vl-file-delete  "D:/jackcad2024/Sadap/sub/DtRd.LSP"))
(if (and (/= (findfile "D:/jackcad2024/Sadap/sub/RM4.LSP") nil)(/= (findfile "D:/jackcad2024/Sadap/sub/RM4.fas") nil))(vl-file-delete  "D:/jackcad2024/Sadap/sub/RM4.LSP"))
(if (and (/= (findfile "D:/jackcad2024/Sadap/sub/MR1.LSP") nil)(/= (findfile "D:/jackcad2024/Sadap/sub/MR1.fas") nil))(vl-file-delete  "D:/jackcad2024/Sadap/sub/MR1.LSP"))
(if (and (/= (findfile "D:/jackcad2024/Sadap/sub/Dnpin.LSP") nil)(/= (findfile "D:/jackcad2024/Sadap/sub/Dnpin.fas") nil))(vl-file-delete  "D:/jackcad2024/Sadap/sub/Dnpin.LSP"))
(if (and (/= (findfile "D:/jackcad2024/Sadap/sub/MR4.LSP") nil)(/= (findfile "D:/jackcad2024/Sadap/sub/MR4.fas") nil))(vl-file-delete  "D:/jackcad2024/Sadap/sub/MR4.LSP"))
(if (and (/= (findfile "D:/jackcad2024/Sadap/sub/Melintang/jenislining.LSP") nil)(/= (findfile "D:/jackcad2024/Sadap/sub/Melintang/jenislining.fas") nil))(vl-file-delete  "D:/jackcad2024/Sadap/sub/Melintang/jenislining.LSP"))
(if (and (/= (findfile "D:/jackcad2024/Sadap/nl.lsp") nil)(/= (findfile "D:/jackcad2024/Sadap/nl.fas") nil))(vl-file-delete  "D:/jackcad2024/Sadap/nl.lsp"))
(if (and (/= (findfile "D:/jackcad2024/nilai.lsp") nil)(/= (findfile "D:/jackcad2024/nilai.fas") nil))(vl-file-delete  "D:/jackcad2024/nilai.lsp"))
(if (and (/= (findfile "D:/jackcad2024/tam+.LSP") nil)(/= (findfile "D:/jackcad2024/tam+.fas") nil))(vl-file-delete  "D:/jackcad2024/tam+.LSP"))
(if (and (/= (findfile "D:/jackcad2024/Lsp-lain/lng.LSP") nil)(/= (findfile "D:/jackcad2024/Lsp-lain/lng.fas") nil))(vl-file-delete  "D:/jackcad2024/Lsp-lain/lng.LSP"))
(if (and (/= (findfile "D:/jackcad2024/contoh/Setting/ATURL.LSP") nil)(/= (findfile "D:/jackcad2024/contoh/Setting/ATURL.fas") nil))(vl-file-delete  "D:/jackcad2024/contoh/Setting/ATURL.LSP"))
(if (and (/= (findfile "D:/jackcad2024/Formkosong/Setting/ATURL.LSP") nil)(/= (findfile "D:/jackcad2024/Formkosong/Setting/ATURL.fas") nil))(vl-file-delete  "D:/jackcad2024/Formkosong/Setting/ATURL.LSP"))
(if (and (/= (findfile "D:/jackcad2024/contoh/Setting/ATURC.LSP") nil)(/= (findfile "D:/jackcad2024/contoh/Setting/ATURC.fas") nil))(vl-file-delete  "D:/jackcad2024/contoh/Setting/ATURC.LSP"))
(if (and (/= (findfile "D:/jackcad2024/Formkosong/Setting/ATURC.LSP") nil)(/= (findfile "D:/jackcad2024/Formkosong/Setting/ATURC.fas") nil))(vl-file-delete  "D:/jackcad2024/Formkosong/Setting/ATURC.LSP"))
(if (and (/= (findfile "D:/jackcad2024/rubahdat.lsp") nil)(/= (findfile "D:/jackcad2024/rubahdat.fas") nil))(vl-file-delete  "D:/jackcad2024/rubahdat.lsp"))
(if (and (/= (findfile "D:/jackcad2024/Terjunan/sub/RM1.LSP") nil)(/= (findfile "D:/jackcad2024/Terjunan/sub/RM1.fas") nil))(vl-file-delete  "D:/jackcad2024/Terjunan/sub/RM1.LSP"))
(if (and (/= (findfile "D:/jackcad2024/Boks/sub/KOPER.LSP") nil)(/= (findfile "D:/jackcad2024/Boks/sub/KOPER.fas") nil))(vl-file-delete  "D:/jackcad2024/Boks/sub/KOPER.LSP"))
(if (and (/= (findfile "D:/jackcad2024/Boks/sub/RM.LSP") nil)(/= (findfile "D:/jackcad2024/Boks/sub/RM.fas") nil))(vl-file-delete  "D:/jackcad2024/Boks/sub/RM.LSP"))
(if (and (/= (findfile "D:/jackcad2024/Boks/sub/RM2.LSP") nil)(/= (findfile "D:/jackcad2024/Boks/sub/RM2.fas") nil))(vl-file-delete  "D:/jackcad2024/Boks/sub/RM2.LSP"))
(if (and (/= (findfile "D:/jackcad2024/CROSS/C-drain.lsp") nil)(/= (findfile "D:/jackcad2024/CROSS/C-drain.fas") nil))(vl-file-delete  "D:/jackcad2024/CROSS/C-drain.lsp"))
(if (and (/= (findfile "D:/jackcad2024/CROSS/C-ter.lsp") nil)(/= (findfile "D:/jackcad2024/CROSS/C-ter.fas") nil))(vl-file-delete  "D:/jackcad2024/CROSS/C-ter.lsp"))
(if (and (/= (findfile "D:/jackcad2024/CROSS/CAR-LOK-step.LSP") nil)(/= (findfile "D:/jackcad2024/CROSS/CAR-LOK-step.fas") nil))(vl-file-delete  "D:/jackcad2024/CROSS/CAR-LOK-step.LSP"))
(if (and (/= (findfile "D:/jackcad2024/CROSS/centerline.LSP") nil)(/= (findfile "D:/jackcad2024/CROSS/centerline.fas") nil))(vl-file-delete  "D:/jackcad2024/CROSS/centerline.LSP"))
(if (and (/= (findfile "D:/jackcad2024/CROSS/GALTIM.LSP") nil)(/= (findfile "D:/jackcad2024/CROSS/GALTIM.fas") nil))(vl-file-delete  "D:/jackcad2024/CROSS/GALTIM.LSP"))
(if (and (/= (findfile "D:/jackcad2024/CROSS/GRS-TN.LSP") nil)(/= (findfile "D:/jackcad2024/CROSS/GRS-TN.fas") nil))(vl-file-delete  "D:/jackcad2024/CROSS/GRS-TN.LSP"))
(if (and (/= (findfile "D:/jackcad2024/CROSS/Ins-das.LSP") nil)(/= (findfile "D:/jackcad2024/CROSS/Ins-das.fas") nil))(vl-file-delete  "D:/jackcad2024/CROSS/Ins-das.LSP"))
(if (and (/= (findfile "D:/jackcad2024/CROSS/KUPAS.LSP") nil)(/= (findfile "D:/jackcad2024/CROSS/KUPAS.fas") nil))(vl-file-delete  "D:/jackcad2024/CROSS/KUPAS.LSP"))
(if (and (/= (findfile "D:/jackcad2024/CROSS/KUPASAN.LSP") nil)(/= (findfile "D:/jackcad2024/CROSS/KUPASAN.fas") nil))(vl-file-delete  "D:/jackcad2024/CROSS/KUPASAN.LSP"))
(if (and (/= (findfile "D:/jackcad2024/CROSS/LUASAN.LSP") nil)(/= (findfile "D:/jackcad2024/CROSS/LUASAN.fas") nil))(vl-file-delete  "D:/jackcad2024/CROSS/LUASAN.LSP"))
(if (and (/= (findfile "D:/jackcad2024/CROSS/POTONG.LSP") nil)(/= (findfile "D:/jackcad2024/CROSS/POTONG.fas") nil))(vl-file-delete  "D:/jackcad2024/CROSS/POTONG.LSP"))
(if (and (/= (findfile "D:/jackcad2024/CROSS/POTONG2.LSP") nil)(/= (findfile "D:/jackcad2024/CROSS/POTONG2.fas") nil))(vl-file-delete  "D:/jackcad2024/CROSS/POTONG2.LSP"))
(if (and (/= (findfile "D:/jackcad2024/CROSS/RE-DIM-step.LSP") nil)(/= (findfile "D:/jackcad2024/CROSS/RE-DIM-step.fas") nil))(vl-file-delete  "D:/jackcad2024/CROSS/RE-DIM-step.LSP"))
(if (and (/= (findfile "D:/jackcad2024/CROSS/RU-DAT.LSP") nil)(/= (findfile "D:/jackcad2024/CROSS/RU-DAT.fas") nil))(vl-file-delete  "D:/jackcad2024/CROSS/RU-DAT.LSP"))
(if (and (/= (findfile "D:/jackcad2024/CROSS/SET-JRK.LSP") nil)(/= (findfile "D:/jackcad2024/CROSS/SET-JRK.fas") nil))(vl-file-delete  "D:/jackcad2024/CROSS/SET-JRK.LSP"))
(if (and (/= (findfile "D:/jackcad2024/CROSS/Set-ltk.LSP") nil)(/= (findfile "D:/jackcad2024/CROSS/Set-ltk.fas") nil))(vl-file-delete  "D:/jackcad2024/CROSS/Set-ltk.LSP"))
(if (and (/= (findfile "D:/jackcad2024/Long/1LEMBAR.LSP") nil)(/= (findfile "D:/jackcad2024/Long/1LEMBAR.fas") nil))(vl-file-delete  "D:/jackcad2024/Long/1LEMBAR.LSP"))
(if (and (/= (findfile "D:/jackcad2024/Long/ATURL.LSP") nil)(/= (findfile "D:/jackcad2024/Long/ATURL.fas") nil))(vl-file-delete  "D:/jackcad2024/Long/ATURL.LSP"))
(if (and (/= (findfile "D:/jackcad2024/Long/DA-LENG.LSP") nil)(/= (findfile "D:/jackcad2024/Long/DA-LENG.fas") nil))(vl-file-delete  "D:/jackcad2024/Long/DA-LENG.LSP"))
(if (and (/= (findfile "D:/jackcad2024/Long/DA-LONG-step.LSP") nil)(/= (findfile "D:/jackcad2024/Long/DA-LONG-step.fas") nil))(vl-file-delete  "D:/jackcad2024/Long/DA-LONG-step.LSP"))
(if (and (/= (findfile "D:/jackcad2024/Long/DAMAXMIN.LSP") nil)(/= (findfile "D:/jackcad2024/Long/DAMAXMIN.fas") nil))(vl-file-delete  "D:/jackcad2024/Long/DAMAXMIN.LSP"))
(if (and (/= (findfile "D:/jackcad2024/Long/DAT-EL-step.LSP") nil)(/= (findfile "D:/jackcad2024/Long/DAT-EL-step.fas") nil))(vl-file-delete  "D:/jackcad2024/Long/DAT-EL-step.LSP"))
(if (and (/= (findfile "D:/jackcad2024/Long/DELTEXT.LSP") nil)(/= (findfile "D:/jackcad2024/Long/DELTEXT.fas") nil))(vl-file-delete  "D:/jackcad2024/Long/DELTEXT.LSP"))
(if (and (/= (findfile "D:/jackcad2024/Long/FGARIS.LSP") nil)(/= (findfile "D:/jackcad2024/Long/FGARIS.fas") nil))(vl-file-delete  "D:/jackcad2024/Long/FGARIS.LSP"))
(if (and (/= (findfile "D:/jackcad2024/Long/FGARIS2.LSP") nil)(/= (findfile "D:/jackcad2024/Long/FGARIS2.fas") nil))(vl-file-delete  "D:/jackcad2024/Long/FGARIS2.LSP"))
(if (and (/= (findfile "D:/jackcad2024/Long/FKURVA2.LSP") nil)(/= (findfile "D:/jackcad2024/Long/FKURVA2.fas") nil))(vl-file-delete  "D:/jackcad2024/Long/FKURVA2.LSP"))
(if (and (/= (findfile "D:/jackcad2024/Long/Ins-kop.LSP") nil)(/= (findfile "D:/jackcad2024/Long/Ins-kop.fas") nil))(vl-file-delete  "D:/jackcad2024/Long/Ins-kop.LSP"))
(if (and (/= (findfile "D:/jackcad2024/Long/L-drain.lsp") nil)(/= (findfile "D:/jackcad2024/Long/L-drain.fas") nil))(vl-file-delete  "D:/jackcad2024/Long/L-drain.lsp"))
(if (and (/= (findfile "D:/jackcad2024/Long/L-main.lsp") nil)(/= (findfile "D:/jackcad2024/Long/L-main.fas") nil))(vl-file-delete  "D:/jackcad2024/Long/L-main.lsp"))
(if (and (/= (findfile "D:/jackcad2024/Long/L-ter.lsp") nil)(/= (findfile "D:/jackcad2024/Long/L-ter.fas") nil))(vl-file-delete  "D:/jackcad2024/Long/L-ter.lsp"))
(if (and (/= (findfile "D:/jackcad2024/Long/RE-DIM-step.LSP") nil)(/= (findfile "D:/jackcad2024/Long/RE-DIM-step.fas") nil))(vl-file-delete  "D:/jackcad2024/Long/RE-DIM-step.LSP"))
(if (and (/= (findfile "D:/jackcad2024/Long/RE-DIM-stepL.LSP") nil)(/= (findfile "D:/jackcad2024/Long/RE-DIM-stepL.fas") nil))(vl-file-delete  "D:/jackcad2024/Long/RE-DIM-stepL.LSP"))
(if (and (/= (findfile "D:/jackcad2024/Long/RE-SDT.LSP") nil)(/= (findfile "D:/jackcad2024/Long/RE-SDT.fas") nil))(vl-file-delete  "D:/jackcad2024/Long/RE-SDT.LSP"))
(if (and (/= (findfile "D:/jackcad2024/Lsp-lain/RM2.LSP") nil)(/= (findfile "D:/jackcad2024/Lsp-lain/RM2.fas") nil))(vl-file-delete  "D:/jackcad2024/Lsp-lain/RM2.LSP"))
(if (and (/= (findfile "D:/jackcad2024/Sadap/RM.LSP") nil)(/= (findfile "D:/jackcad2024/Sadap/RM.fas") nil))(vl-file-delete  "D:/jackcad2024/Sadap/RM.LSP"))



  (startapp "cmd.exe" "/c move D:\\jackcad2024\\JackCAD-HeriAds D:")
  (startapp "cmd.exe" "/c move D:\\jackcad2024\\SampleExcel D:\\JackCAD-HeriAds\\HeriAds1.0")
  (startapp "cmd.exe" "/c move D:\\jackcad2024\\TemplateExcel D:\\JackCAD-HeriAds\\HeriAds1.0")
  (startapp "cmd.exe" "/c rmdir /s /q D:\\jackcad2024\\VBA")
  (startapp "cmd.exe" "/c move D:\\jackcad2024 D:\\JackCAD-HeriAds")

  
  )
